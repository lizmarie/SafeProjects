FME workspace GISandCADWorkflows.fmw

Parameters:
- SourceDataset_MITAB = C:\FMEData2017\Data\Transportation\Parking\Meters.tab   # Source MapInfo TAB File(s)
- file = RoadNetwork.dwg   # File
- SourceDataset_ACAD = fme://autodesk-a360/CompleteRoads.dwg?id=a.cGVyc29uYWw6dWUyYjA1NTAyIzIwMTcwODE2ODgyNjE1MzE%2Fitems%2Furn%3Aadsk.wipprod%3Adm.lineage%3Ajeo5OPMxR9OajwgJvSJqCw&connection=lsanderson%20Autodesk%20A360   # Source Autodesk AutoCAD DWG/DXF File(s)
- SourceDataset_ACAD_5 = fme://autodesk-a360/TrafficSignals.dwg?id=a.cGVyc29uYWw6dWUyYjA1NTAyIzIwMTcwODE2ODgyNjE1MzE%2Fitems%2Furn%3Aadsk.wipprod%3Adm.lineage%3AzZE1VelIT6-TrXADgggX2A&connection=lsanderson%20Autodesk%20A360   # Source Autodesk AutoCAD DWG/DXF File(s)

Readers:
- ACAD_1: ACAD from $(SourceDataset_ACAD) in LL84
- ACAD_2: ACAD from $(SourceDataset_ACAD_5) in LL84
- MITAB_1: MITAB from $(SourceDataset_MITAB) in LL84

Note: CompleteRoads [ACAD] / Coord. System: LL84
DWGStyler_5_DWGStyled_-__FeatureWriter_Layer1: Junction
    -> FeatureWriter [Layer1]
Note: Writer: / Format: ACAD / Dataset: $(file) / Coordinate System: Same as source / Feature Types: / Traffic Signals / Roads / Parking Meters / Create a new User Parameter for the Dataset, for the Default Value call it RoadNetwork.dwg
FeatureWriter
    ACAD_VERSION = Release2013
    ACAD_COORDINATE_SYSTEM_STORAGE = NONE
    ACAD_DEFAULT_ATTR_STORAGE = extended_entity_data
    DATASET = $(file)
    ACAD_OUTPUT_DEFINED_ATTRS_ONLY = yes
    ACAD_APPEND_TO_TEMPLATEFILE = no
    ACAD_PRESERVE_TEMPLATE_PAPER_SPACE_ENTITIES = yes
    FEATURE_TYPE_LIST_ATTR = _feature_type
    ACAD_PREFER_DONUTS_AS_HATCHES = no
    FORMAT = ACAD
    ACAD_AUDIT_AND_FIX = yes
    ACAD_USE_BLOCK_NAME_FOR_CREATION = no
    ACAD_PURGE = no
    ACAD_WRITE_THUMBNAIL_IMAGE = no
    TOTAL_FEATURES_WRITTEN_ATTR = _total_features_written
    DATASET_ATTR = _dataset
    ACAD_DESTINATION_DATASETTYPE_VALIDATION = Yes
    SUMMARY -> AutodeskA360Connector
Note: Request: / Autodesk A360 Action: Upload / Autodesk A360 Account: (your Autodesk A360 connection) / Source: / Upload: File / File to Upload: $(file) <-- User Parameter created in the FeatureWriter / Upload New Version: Yes / AutoDesk A360 Destination: / Folder ID: (your Autodesk A360 Project folder location)
AutodeskA360Connector
    PARAMETER_SETUP = SOURCE;;_FME_SOURCE_TYPE;File;_FME_SOURCE_FILE;$(file);_FME_SOURCE_FOLDER;<Unused>;_FME_INCLUDE_SUBFOLDERS;<Unused>;_FME_UPLOAD_VERSION;Yes;_FME_DATA_TO_UPLOAD;<Unused>;DEST;;_FME_UPLOAD_DESTINATION_PATH;a.cGVyc29uYWw6dWUyYjA1NTAyIzIwMTcwODE2ODgyNjE1MzE/folders/urn:adsk.wipprod:fs.folder:co.8UfH2hHVQKiA8lV9zKhvXA[Project];_FME_UPLOAD_ATTR_FILENAME;<Unused>;OUTPUT_ATTR;;_FME_OBJECT_ID_ATTRIBUTE;_id;_FME_OBJECT_URL_ATTRIBUTE;_sharable_link;_FME_OBJECT_DIRECT_URL_ATTRIBUTE;_direct_download_link;FME_CONTROLLER_QUERY_FILE;transformers\dependencies\autodeska360\Upload.fme
    AUTODESK_NAMED_CONNECTION = lsanderson Autodesk A360
    OPERATION_TYPE = Upload

Bookmark: Traffic Signals
Note: TrafficSignals: TrafficSignals [ACAD] / Coord. System: LL84
TrafficSignals (reader ACAD_2)
    -> DWGStyler_Red

Bookmark: Traffic Signal Styles
DWGStyler_Red
    COLOR = 1,0,0
    DWGStyled -> FeatureWriter [Layer100]

Bookmark: Roads
Private (reader ACAD_1)
    -> DWGStyler_Grey
NonCity (reader ACAD_1)
    -> DWGStyler_Grey
Other (reader ACAD_1)
    -> DWGStyler_Grey
Arterial (reader ACAD_1)
    -> DWGStyler_Black
Collector (reader ACAD_1)
    -> DWGStyler_Brown
Secondary (reader ACAD_1)
    -> DWGStyler_Brown
Residential (reader ACAD_1)
    -> DWGStyler_Brown

Bookmark: Road Styles
DWGStyler_Grey
    COLOR = 0.8,0.8,0.8
    DWGStyled -> DWGStyler_5_DWGStyled_-__FeatureWriter_Layer1
DWGStyler_Black
    LINE_SCALE = 2
    COLOR = 0,0,0
    LINE_PATTERNING = Continuous
    LINE_WIDTH = 20
    DWGStyled -> DWGStyler_5_DWGStyled_-__FeatureWriter_Layer1
DWGStyler_Brown
    LINE_SCALE = 1.0
    COLOR = 0.65098,0.407843,0.329412
    LINE_PATTERNING = Continuous
    LINE_WIDTH = 20
    DWGStyled -> DWGStyler_5_DWGStyled_-__FeatureWriter_Layer1

Bookmark: Parking Meters
Note: Meters: Meters [MITAB] / Coord. System: LL84
Meters (reader MITAB_1)
    attributes: HourlyRate decimal(8,2), TimeLimit decimal(8,2), CreditCard logical, PayPhone largeint, MeterType char(20), Neighborhood char(20)
    -> DWGStyler_Green

Bookmark: Parking Meter Styles
DWGStyler_Green
    COLOR = 0,0.666667,0
    DWGStyled -> FeatureWriter [Layer101]
