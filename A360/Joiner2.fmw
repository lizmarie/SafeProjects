FME workspace Joiner2.fmw

Parameters:
- _FME_DATA_TARGET = Folder   # Download as

Creator
    GEOMTYPE = Geometry Object
    NUM = 1
    CREATED -> AutodeskA360Connector
AutodeskA360Connector
    OPERATION_TYPE = Download
    AUTODESK_NAMED_CONNECTION = lsanderson Autodesk A360
    PARAMETER_SETUP = SOURCE;;_FME_FILES;a.cGVyc29uYWw6dWUyYjA1NTAyIzIwMTcwODE2ODgyNjE1MzE/folders/urn:adsk.wipprod:fs.folder:co.1dpoN0UpQwOrjzw7pg-yvQ;DEST;;_FME_DATA_TARGET;$(_FME_DATA_TARGET);_FME_INCLUDE_SUBFOLDERS;Yes;_FME_TARGET_FOLDER;C:\Users\lsanderson\Downloads;_FME_TARGET_ATTRIBUTE;_contents;FME_CONTROLLER_QUERY_FILE;transformers\dependencies\autodeska360\Download.fme
    -> FeatureReader [INITIATOR]
FeatureReader
    ACAD_STORE_SPLINE_DEFS = yes
    ACAD_XRECORD_READING = None
    ACAD_PRESERVE_INSERTS = no
    ACAD_READ_SYS_VARS = no
    ACAD_RESOLVE_DIMENSIONS = yes
    COMBINE_GEOM = Use Result
    ACAD_READ_XREFS = no
    ACAD_STORE_INSERT_POINT = no
    ACAD_IGNORE_UCS = no
    ACAD_LIST_ATTRIBUTE_ENTITY_DATA = yes
    ACAD_RESOLVE_BLOCKS = yes
    ATTRIBUTES = 0,,"Parking Meters",,Roads,,"Traffic Signals",
    ACAD_PRESERVE_CLIPPED_RASTERS = no
    ACAD_ALL_MERGED_FILTERS_NEED_NO_DEFS = Yes
    ACAD_STORE_BULGE_INFO = no
    OUTPUT_FEATURES_DISPLAY = Schema and Data Features
    ACAD_EVALUATE_MLINE_GEOM = no
    ACAD_PRESERVE_COMPLEX_HATCHES = no
    ACAD_IGNORE_FROZEN_LAYERS = no
    ACAD_USE_BLOCK_HEADER_LAYER = yes
    FORMAT = ACAD
    ACAD_METAFILE = acad
    ACAD_READ_AS_2_5D = no
    ACAD_READ_USER_DICTIONARIES = no
    ACAD_READ_MODEL_SPACE = yes
    DATASET = C:\Users\lsanderson\Downloads\Joining Data\*.dwg
    ACAD_RESOLVE_ENTITY_COLOR = yes
    ACAD_USE_BLOCK_LAYER_INFO = no
    ACAD_EXPLODE_MTEXT = yes
    ACAD_LIST_EXTENDED_DATA = yes
    ACAD_OUTPUT_ZERO_LENGTH_LINES_AS_LINES = no
    ATTR_ACCUM_MODE = Only Use Result
    ACAD_USE_SEARCH_ENVELOPE = NO
    ACAD_INTERPRET_EXTENDED_DATA = yes
    ACAD_READ_GROUPS = no
    ACAD_QUERY_FEATURE_TYPES_FOR_MERGE_FILTERS = Yes
    ACAD_APPLY_WORLD_FILE = yes
    ACAD_STRUCTURE_EXTENDED_DATA = no
    ACAD_CONVERT_ZERO_LENGTH_ARCS_TO_POINTS = yes
    INTERACT = <No Spatial Filter>
    ACAD_VISIBLE_ATTRIBUTES_AS_TEXT = yes
    ACAD_READ_PROXY_GRAPHICS = yes
    ACAD_STORE_LAYER_INFO = no
    ACAD_READ_PAPER_SPACE = NO
    <SCHEMA> -> FeatureReader__Schema_
    <OTHER> -> FeatureReader__Generic_
    INITIATOR -> FeatureReader__Initiator_
    <REJECTED> -> FeatureReader__Rejected_
FeatureReader__Schema_: Logger
    MAXCOORDS = 20
    MAXFEATS = 20
    MESSAGE = Feature is:
FeatureReader__Generic_: Logger
    MAXCOORDS = 20
    MAXFEATS = 20
    MESSAGE = Feature is:
FeatureReader__Initiator_: Logger
    MAXCOORDS = 20
    MAXFEATS = 20
    MESSAGE = Feature is:
FeatureReader__Rejected_: Logger
    MAXCOORDS = 20
    MAXFEATS = 20
    MESSAGE = Feature is:
