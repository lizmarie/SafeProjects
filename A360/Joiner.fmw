FME workspace Joiner.fmw

AutodeskA360Connector
    AUTODESK_NAMED_CONNECTION = lsanderson Autodesk A360
    PARAMETER_SETUP = SOURCE;;_FME_FILES;a.cGVyc29uYWw6dWUyYjA1NTAyIzIwMTcwODE2ODgyNjE1MzE/folders/urn:adsk.wipprod:fs.folder:co.1dpoN0UpQwOrjzw7pg-yvQ;DEST;;_FME_DATA_TARGET;Folder;_FME_INCLUDE_SUBFOLDERS;Yes;_FME_TARGET_FOLDER;C:\Users\lsanderson\Documents\Articles\A360;_FME_TARGET_ATTRIBUTE;<Unused>;FME_CONTROLLER_QUERY_FILE;transformers\dependencies\autodeska360\Download.fme
    OPERATION_TYPE = Download
    -> FeatureReader [INITIATOR]
FeatureReader
    ACAD_READ_PROXY_GRAPHICS = yes
    ACAD_USE_SEARCH_ENVELOPE = NO
    ACAD_READ_PAPER_SPACE = NO
    ACAD_METAFILE = acad
    ACAD_EXPLODE_MTEXT = yes
    ACAD_XRECORD_READING = None
    ACAD_OUTPUT_ZERO_LENGTH_LINES_AS_LINES = no
    ACAD_INTERPRET_EXTENDED_DATA = yes
    ACAD_IGNORE_UCS = no
    OUTPUT_FEATURES_DISPLAY = Schema and Data Features
    ACAD_PRESERVE_CLIPPED_RASTERS = no
    ACAD_PRESERVE_INSERTS = no
    ACAD_READ_MODEL_SPACE = yes
    COMBINE_GEOM = Use Result
    ACAD_APPLY_WORLD_FILE = yes
    ACAD_CONVERT_ZERO_LENGTH_ARCS_TO_POINTS = yes
    ACAD_USE_BLOCK_LAYER_INFO = no
    ACAD_READ_AS_2_5D = no
    ACAD_READ_GROUPS = no
    ACAD_PRESERVE_COMPLEX_HATCHES = no
    ACAD_QUERY_FEATURE_TYPES_FOR_MERGE_FILTERS = Yes
    ACAD_ALL_MERGED_FILTERS_NEED_NO_DEFS = Yes
    ACAD_READ_SYS_VARS = no
    FORMAT = ACAD
    ACAD_IGNORE_FROZEN_LAYERS = no
    DATASET = $(_FME_TARGET_FOLDER)\streetlighting.dwg
    INTERACT = <No Spatial Filter>
    ACAD_VISIBLE_ATTRIBUTES_AS_TEXT = yes
    ACAD_STORE_INSERT_POINT = no
    ACAD_RESOLVE_ENTITY_COLOR = yes
    ACAD_STRUCTURE_EXTENDED_DATA = no
    ACAD_STORE_LAYER_INFO = no
    ACAD_STORE_SPLINE_DEFS = yes
    ACAD_USE_BLOCK_HEADER_LAYER = yes
    ACAD_READ_USER_DICTIONARIES = no
    ACAD_READ_XREFS = no
    ACAD_STORE_BULGE_INFO = no
    ACAD_EVALUATE_MLINE_GEOM = no
    ACAD_LIST_EXTENDED_DATA = yes
    ACAD_RESOLVE_BLOCKS = yes
    ACAD_LIST_ATTRIBUTE_ENTITY_DATA = yes
    ATTR_ACCUM_MODE = Only Use Result
    ACAD_RESOLVE_DIMENSIONS = yes
