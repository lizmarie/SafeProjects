FME workspace FinishedWorkspace.fmw

Parameters:
- SourceDataset_CSV2 = $(FME_MF_DIR)crime2011.csv   # Source CSV (Comma Separated Value) File(s)
- DestDataset_XLSXW = $(FME_MF_DIR)CrimeByType.xlsx   # Destination Microsoft Excel File

Readers:
- CSV2_1: CSV2 from $(SourceDataset_CSV2)

Writers:
- XLSXW_1: XLSXW to $(DestDataset_XLSXW)

Note: Crime infromation by block number
CSV (reader CSV2_1)
    attributes: CrimeID string, Type string, Month string, Block string
    -> StringReplacer
Note: Replace all the XXs in Block with 00
StringReplacer
    FIND_TEXT = XX
    NO_MATCH = _FME_NO_OP_
    CASE = NO
    REGEXP = NO
    SRC_ATTRS = Block
    REPLACE_TEXT = 00
    -> StringCaseChanger
Note: Change Block from all UPPERCASE to Title Case
StringCaseChanger
    CHANGE_TYPE = Full Title Case
    ATTRCHOICE = Selected Attributes
    ATTRLIST = Block
    -> DatabaseJoiner
DatabaseJoiner
    DATASET = Training
    POSTGIS_USE_TRUE_POSTGIS_TYPES = yes
    POSTGIS_QUERY_FEATURE_TYPES_FOR_MERGE_FILTERS = Yes
    ADDED_FIELDS = type
    POSTGIS_NAMED_CONNECTION = Training
    MATCH_RULE_DISPLAY = Match All (1:M)
    POSTGIS_DISABLE_COLLECTION_SPLITTING = yes
    MATCH_MULTIPLE_DISPLAY = Create a feature for each match
    JOIN_KEYS = Block HBlock
    FORMAT = POSTGIS
    TABLE = public.Roads
    PREFETCH_QUERY = select * from public."Roads"
    CACHE_SIZE = 5000
    ATTR_ACCUM_MODE = Merge Joined
    PREFETCH_EXHAUSTIVE = Yes
    ATTR_CONFLICT_RES = Use Original
    JOINED -> AttributeFilter
    JOINED -> Type (writer XLSXW_1)
    JOINED -> DatabaseJoiner_Joined
DatabaseJoiner_Joined: Inspector

Bookmark: Optional 1
AttributeFilter [off]
    ATTR_NAME = Type
    ATTR_VALUES = Arterial,Collector,NonCity,Other,Private,Residential,Secondary,<Empty>,<Missing>,<Null>,<Unfiltered>
    Arterial -> Inspector [off]
    Collector -> Inspector [off]
    NonCity -> Inspector [off]
    Other -> Inspector [off]
    Private -> Inspector [off]
    Residential -> Inspector [off]
    Secondary -> Inspector [off]
Note: Filter by imported Type from public.Roads
Inspector [off]

Bookmark: Optional 2
Note: Write out to an Excel spreadsheet with each Type as an individual sheet
Type (writer XLSXW_1) [off]
    attributes: CrimeID string(20), Type string(20), Month string(20), Block string(20), type auto(20), _matched_records auto(20)
