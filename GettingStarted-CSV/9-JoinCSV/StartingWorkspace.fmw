FME workspace StartingWorkspace.fmw

Parameters:
- SourceDataset_CSV2 = $(FME_MF_DIR)crime2011.csv   # Source CSV (Comma Separated Value) File(s)

Readers:
- CSV2_1: CSV2 from $(SourceDataset_CSV2)

Note: Crime infromation by block number
CSV (reader CSV2_1)
    attributes: CrimeID string, Type string, Month string, Block string
    -> StringReplacer
Note: Replace all the XXs in Block with 00
StringReplacer
    FIND_TEXT = XX
    NO_MATCH = _FME_NO_OP_
    CASE = NO
    REGEXP = NO
    SRC_ATTRS = Block
    REPLACE_TEXT = 00
    -> StringCaseChanger
Note: Change Block from all UPPERCASE to Title Case
StringCaseChanger
    CHANGE_TYPE = Full Title Case
    ATTRCHOICE = Selected Attributes
    ATTRLIST = Block
