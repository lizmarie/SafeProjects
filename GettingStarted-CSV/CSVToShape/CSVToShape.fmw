FME workspace CSVToShape.fmw
Title: csv2shape

Parameters:
- SourceDataset_CSV2 = $(FME_MF_DIR)major_roads.csv   # Source CSV (Comma Separated Value) File(s)
- DestDataset_ESRISHAPE = C:\Users\lsanderson\Documents\SafeProjects\GettingStarted-CSV   # Destination Esri Shapefile Folder

Readers:
- CSV2_1: CSV2 from $(SourceDataset_CSV2)

Writers:
- ESRISHAPE_1: ESRISHAPE to $(DestDataset_ESRISHAPE)

Bookmark: Join CSV and MS Access data together and write to Shapefile
Note: CSV: major_roads [CSV2]
CSV (reader CSV2_1)
    attributes: road_id string, vertex_num string, x string, y string
    -> VertexCreator
VertexCreator
    XVAL = @Value(x)
    YVAL = @Value(y)
    MODE_NAME = Add Point
    -> LineBuilder
Note: Connection Break Attribute: roads_id
LineBuilder
    ACCUM_INPUT_ATTRS = Use Attributes From One Feature
    BREAKATTR = road_id
    LINE -> DatabaseJoiner
Note: DatabaseJoiner [DatabaseJoiner] / Format: MDB_ADO / Dataset: road_attrs.mdb / Join: / Table: major_roads / Join On: road_id ROAD_ID / Fields to Add: PRIMARY_DIRECTION ROAD_CATEGORY / ROAD_ID ROAD_NAME TYPE_CODE / Cardinality: Match All (1:M) / Multiple Matches: Create a feature for each match / Merge Attributes: / Accumulation Mode: Merge Joined / Conflict Resolution: Use Original
DatabaseJoiner
    TABLE = major_roads
    MATCH_RULE_DISPLAY = Match All (1:M)
    ATTR_CONFLICT_RES = Use Original
    ADDED_FIELDS = PRIMARY_DIRECTION ROAD_CATEGORY ROAD_ID ROAD_NAME TYPE_CODE
    FORMAT = MDB_ADO
    CACHE_SIZE = 5000
    JOIN_KEYS = road_id ROAD_ID
    DATASET = $(FME_MF_DIR_ENCODED)road_attrs.mdb
    MATCH_MULTIPLE_DISPLAY = Create a feature for each match
    PREFETCH_EXHAUSTIVE = Yes
    ATTR_ACCUM_MODE = Merge Joined
    JOINED -> Roads (writer ESRISHAPE_1)
Note: Roads: GettingStarted-CSV [ESRISHAPE]
Roads (writer ESRISHAPE_1)
    attributes: PRIMARY_DI char(200), ROAD_CATEG char(200), ROAD_ID char(200), ROAD_NAME char(200), TYPE_CODE char(200)
