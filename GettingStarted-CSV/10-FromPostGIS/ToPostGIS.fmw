FME workspace ToPostGIS.fmw

Parameters:
- SourceDataset_CSV2 = C:\FMEData2017\ArticleData\libraries.csv   # Source CSV (Comma Separated Value) File(s)
- SourceDataset_ESRISHAPE = C:\FMEData2017\Data\Boundaries\local_area_boundary.shp   # Source Esri Shapefile(s)
- DestDataset_POSTGIS = Training   # Connection

Readers:
- CSV2_1: CSV2 from $(SourceDataset_CSV2) in LL84
- ESRISHAPE_1: ESRISHAPE from $(SourceDataset_ESRISHAPE)

Writers:
- POSTGIS_1: POSTGIS to $(DestDataset_POSTGIS) in LL84

Note: local_area_boundary [ESRISHAPE]
local_area_boundary (reader ESRISHAPE_1)
    attributes: MAPID char(20), NAME char(254)
    -> Reprojector
Note: Reproject from UTM83-10 to LL84
Reprojector
    DEST = LL84
    SOURCE = Read from feature
    INTERPOLATION_TYPE_NAME = Nearest Neighbor
    RASTER_CELL_SIZE = Preserve Cells
    REPROJECTED -> PointOnAreaOverlayer [AREA]
Note: CSV: libraries [CSV2]
CSV (reader CSV2_1)
    attributes: LIBRARY_NAME string, LATITUDE y_coordinate, LONGITUDE x_coordinate, ADDRESS string, URLLINK string
    -> PointOnAreaOverlayer [POINT]
PointOnAreaOverlayer
    OV_ATTR = _overlaps
    ATTR_ACCUM_MODE = Merge Incoming
    POLYS_FIRST = NO
    DEAGGREGATE_INPUT = Yes
    ATTR_CONFLICT_RES = Use Original
    POINT -> AttributeManager
Note: Remove MAPID and _overlaps / Rename Name to NEIGHBORHOOD
AttributeManager
    ATTR_TABLE:
      REMOVE MAPID
      RENAME_SET_VALUE NAME > NEIGHBORHOOD
      REMOVE _overlaps
    -> Libraries (writer POSTGIS_1)
Note: fmedata2015.Libraries: Training [POSTGIS]
Libraries (writer POSTGIS_1)
    attributes: library_name text, latitude float8, longitude float8, address text, urllink text, neighborhood varchar(200)
