FME workspace CSVTo.fmw
Title: FromCSV
Description: Demonstrates different methods of converting CSV to spatial data

Parameters:
- SourceDataset_CSV2_5 = $(FME_MF_DIR)rapid_transit_line.csv   # Source CSV (Comma Separated Value) File(s)
- SourceDataset_CSV2 = $(FME_MF_DIR)Neighborhoods.csv   # Source CSV (Comma Separated Value) File(s)
- SourceDataset_CSV2_7 = $(FME_MF_DIR)rapid_transit_stations.csv   # Source CSV (Comma Separated Value) File(s)
- SourceDataset_CSV2_6 = $(FME_MF_DIR)CulturalSpaces2016.csv   # Source CSV (Comma Separated Value) File(s)

Readers:
- CSV2_1: CSV2 from $(SourceDataset_CSV2_5) in UTM83-10
- CSV2_2: CSV2 from $(SourceDataset_CSV2) in LL84
- CSV2_3: CSV2 from $(SourceDataset_CSV2_7) in UTM83-10
- CSV2_4: CSV2 from $(SourceDataset_CSV2_6)

Bookmark: Point
Note: General Parameters: / Reader Type: CSV (Comma Separated Value) / CSV File Name: CSV / Reader: rapid_transit_stations [CSV2] / Allowed Geometries: All / Exposed Attributes: NameTypeSTATIONstringxx_coordinateyy_coordinate
CSV (reader CSV2_3)
    attributes: STATION string, x x_coordinate, y y_coordinate
    -> CSV
Note: To create Point features: / a) Set the data type in the Reader Parameters by setting the Attribute Definition to Manual then setting the Data Type to x_coordinate and y_coordinate / OR / b) Use the VertexCreator (shown for the Line and Polygon features) by setting the x and y values / OR / c) Geocoding, see the bookmark Geocoding Method for more information
CSV: Inspector

Bookmark: Line
Note: General Parameters: / Reader Type: CSV (Comma Separated Value) / CSV File Name: CSV / Reader: rapid_transit_line [CSV2] / Allowed Geometries: All / Exposed Attributes: NameTypeLINEstringxstringystring
CSV (reader CSV2_1)
    attributes: LINE string, x string, y string
    -> VertexCreator
VertexCreator
    MODE_NAME = Add Point
    XVAL = @Value(x)
    YVAL = @Value(y)
    -> LineBuilder
Note: To create Line features: / Use either a or b as explained for Point to set the x and y values to create vertices, then use the LineBuilder and set the Connection Break Attributes to LINE, this will break the line each time the rail line name changes
LineBuilder
    ACCUM_INPUT_ATTRS = Use Attributes From One Feature
    BREAKATTR = LINE
    LINE -> LineBuilder_Line
LineBuilder_Line: Inspector

Bookmark: Polygon
Note: CSV: Neighborhoods [CSV2]
CSV (reader CSV2_2)
    attributes: NeighborhoodName string, x string, y string
    -> VertexCreator_2
VertexCreator_2
    MODE_NAME = Add Point
    XVAL = @Value(x)
    YVAL = @Value(y)
    -> LineBuilder_2
LineBuilder_2
    ACCUM_INPUT_ATTRS = Use Attributes From One Feature
    BREAKATTR = NeighborhoodName
    POLYGON -> LineBuilder_2_Line
Note: To create Polygon features: / Use either a or b as explained for Point to set the x and y values to create vertices, then use the LineBuilder and set the Connection Break Attributes to NeighborhoodName, the line will circle back to the original point if a point is shared by two lines to create a polygon, the line will only break once the NeighborhoodName is changed
LineBuilder_2_Line: Inspector

Bookmark: Geocoding Method
Note: CSV: CulturalSpaces2016 [CSV2]
CSV (reader CSV2_4)
    attributes: CULTURAL_SPACE_NAME string, WEBSITE string, TYPE string, PRIMARY_USE string, ADDRESS string, LOCAL_AREA string, OWNERSHIP string, SQUARE_FEET string, NUMBER_OF_SEATS string, ACTIVE_SPACE string
    -> Geocoder
Geocoder
    THREADS = 4
    GEOCODING_SERVICE = Google
    TIMEOUT = 60
    -> Inspector
Note: Using Geocoding: / There are the two methods for obtaining points when working with CSV data if you have x/y/z information, but what if you don't. You can use the Geocoder tranformer and create points from addresses. Just sign up for a free geocoding service, add the API and set the Street Address to ADDRESS
Inspector
