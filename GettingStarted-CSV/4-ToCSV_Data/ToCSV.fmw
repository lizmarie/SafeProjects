FME workspace ToCSV.fmw

Parameters:
- SourceDataset_ESRISHAPE = $(FME_MF_DIR)rapid_transit_line.shp   # Source Esri Shapefile(s)
- DestDataset_CSV2 = C:\Users\lsanderson\Documents\SafeProjects\GettingStarted-CSV\4-ToCSV_Data   # Destination CSV (Comma Separated Value) Folder
- SourceDataset_XLSXR = $(FME_MF_DIR)CensusLocalAreaProfiles2011.xls   # Source Microsoft Excel File(s)
- DestDataset_CSV2_4 = C:\Users\lsanderson\Documents\SafeProjects\GettingStarted-CSV\ToCSV_Data   # Destination CSV (Comma Separated Value) Folder

Readers:
- ESRISHAPE_1: ESRISHAPE from $(SourceDataset_ESRISHAPE) in UTM83-10
- XLSXR_1: XLSXR from $(SourceDataset_XLSXR)

Writers:
- CSV2_1: CSV2 to $(DestDataset_CSV2)
- CSV2_2: CSV2 to $(DestDataset_CSV2_4)

Bookmark: Part 1: Tabular to Tabular CSV
Note: 2011 Local Areas: CensusLocalAreaProfiles2011 [XLSXR]
2011 Local Areas (reader XLSXR_1)
    attributes: A char(102), Arbutus-Ridge number(8,1), Downtown number(8,1), Dunbar-Southlands number(8,1), Fairview number(8,1), Grandview-Woodland number(8,1), Hastings-Sunrise number(8,1), Kensington-Cedar Cottage number(8,1), Kerrisdale number(8,1), Killarney number(8,1), Kitsilano number(8,1), Marpole number(8,1), Mount Pleasant number(8,1), Oakridge number(8,1), Renfrew-Collingwood number(8,1), Riley Park number(8,1), Shaughnessy number(7,1), South Cambie number(7,1), Strathcona number(8,1), Sunset number(8,1), Victoria-Fraserview number(8,1), West End number(8,1), West Point Grey number(8,1), Vancouver CSD (City) char(7), CMA of Vancouver char(8)
    -> AttributeManager_2
Note: Rename A to CensusType
AttributeManager_2
    ATTR_TABLE = RENAME_SET_VALUE A > CensusType
    -> Tester
Note: Tests for <missing> attributes
Tester
    TEST_DESCRIPTION = "Tests for <missing> attributes "
    TEST_CLAUSE = TEST CensusType ATTRIBUTE_IS_MISSING ""
    BOOL_OP = OR
    TEST_MODE = Automatic
    FAILED -> VancouverCensus2011 (writer CSV2_2)
Note: VancouverCensus2011: GettingStarted-CSV [CSV2]
VancouverCensus2011 (writer CSV2_2)
    attributes: CensusType string, Arbutus-Ridge string, Downtown string, Dunbar-Southlands string, Fairview string, Grandview-Woodland string, Hastings-Sunrise string, Kensington-Cedar Cottage string, Kerrisdale string, Killarney string, Kitsilano string, Marpole string, Mount Pleasant string, Oakridge string, Renfrew-Collingwood string, Riley Park string, Shaughnessy string, South Cambie string, Strathcona string, Sunset string, Victoria-Fraserview string, West End string, West Point Grey string, Vancouver CSD (City) string, CMA of Vancouver string

Bookmark: Part 2: Spatial Shapfile to Spatial CSV
Note: rapid_transit_line: rapid_transit_line [ESRISHAPE]
rapid_transit_line (reader ESRISHAPE_1)
    attributes: LINE char(30)
    -> CoordinateExtractor
Note: Extracts coordinates into a attribute called _indices{}
CoordinateExtractor
    LIST_NAME = _indices
    MODE = All Coordinates
    -> ListExploder
Note: List Attribute: _indices{}
ListExploder
    INDEX_ATTR = _element_index
    LIST_ATTR = _indices{}
    ATTR_ACCUM_MODE = Merge List Attributes
    ATTR_CONFLICT_RES = Use List Attribute Values
    ELEMENTS -> AttributeManager
Note: Remove _element_index and z / Rename x and y to Longitude and Latitude
AttributeManager
    ATTR_TABLE:
      RENAME_SET_VALUE x > Longitude
      RENAME_SET_VALUE y > Latitude
      REMOVE z
      REMOVE _element_index
    -> rapid_transit_line (writer CSV2_1)
Note: rapid_transit_line: GettingStarted-CSV [CSV2]
rapid_transit_line (writer CSV2_1)
    attributes: LINE string, Longitude string, Latitude string
