FME workspace CSVtoChart.fmw
Title: CSVtoChart

Parameters:
- SourceDataset_ESRISHAPE = $(FME_MF_DIR)voting_boundary.shp   # Source Esri Shapefile(s)
- DestDataset_OGCKML = $(FME_MF_DIR)ElectionKml.kml   # Destination Google KML File
- SourceDataset_CSV2 = $(FME_MF_DIR)Vancouver2014ElectionResults.csv   # Source CSV (Comma Separated Value) File(s)

Readers:
- ESRISHAPE_1: ESRISHAPE from $(SourceDataset_ESRISHAPE)
- CSV2_1: CSV2 from $(SourceDataset_CSV2)

Writers:
- OGCKML_1: OGCKML to $(DestDataset_OGCKML)

Note: CSV: Vancouver2014ElectionResults [CSV2]
CSV (reader CSV2_1)
    attributes: CANDIDATE string, Sunset real32, Killarney real32, Renfrew-Collingwood real32, Kensington-Cedar Cottage real32, West End real32, Downtown real32, Kitsilano real32, Victoria-Fraserview real32, Oakridge real32, Kerrisdale real32, Mount Pleasant real32, Marpole real32, Dunbar-Southlands real32, Shaughnessy real32, Hastings-Sunrise real32, Arbutus-Ridge real32, Strathcona real32, Fairview real32, Grandview-Woodland real32, Riley Park real32, South Cambie real32, West Point Grey real32
    -> AttributeExploder
Note: GoogleChartsAPI Example 2017.1 / This workspace uses coordinate data (Esri Shapefile) and joins to election results (CSV). / A Pie Chart is generated using HTML code and the results are exported to KML (viewable in Google Earth).
Note: voting_boundary [ESRISHAPE]
voting_boundary (reader ESRISHAPE_1)
    attributes: VD char(10), NAME char(100), ADDRESS char(100), LOCATION char(100), LATITUDE number(31,15), LONGITUDE number(31,15), ADV_ONLY char(10), LOCAL_AREA char(100), DIVISION char(3), _overlaps char(200)
    -> Dissolver
Note: Elections: ElectionKml [OGCKML]
Elections (writer OGCKML_1)
    attributes: West Point Grey kml_real32, West End kml_real32, VOTE_COUNT kml_char(200), Victoria-Fraserview kml_real32, Sunset kml_real32, Strathcona kml_real32, South Cambie kml_real32, Shaughnessy kml_real32, Riley Park kml_real32, Renfrew-Collingwood kml_real32, Oakridge kml_real32, NAME kml_char(100), Mount Pleasant kml_real32, Marpole kml_real32, LONGITUDE kml_real64, LOCATION kml_char(100), LOCAL_AREA kml_char(100), LATITUDE kml_real64, Kitsilano kml_real32, Killarney kml_real32, Kerrisdale kml_real32, Kensington-Cedar Cottage kml_real32, Hastings-Sunrise kml_real32, Grandview-Woodland kml_real32, Fairview kml_real32, Dunbar-Southlands kml_real32, Downtown kml_real32, DIVISION kml_char(3), CANDIDATE kml_char(255), Arbutus-Ridge kml_real32,
      ADDRESS kml_char(100), _html3 kml_char(200), _html2 kml_char(200), _html1 kml_char(200), _html kml_char(200), _format_candidate kml_char(200)

Bookmark: Create attributes
Note: Creates a new pair of attributes (name/value) / for each feature. This is the critical step to / transform the data into a database-style list
AttributeExploder
    ATTR_NAME_LABEL = LOCATION
    EXPLODING_TYPE = Features
    KEEP_ATTRIBUTES = Yes
    KEEP_GEOMETRY = No
    ATTR_VALUE_LABEL = VOTE_COUNT
    -> Tester
Note: Test for numerical values using Regex
Tester
    TEST_MODE = Automatic
    TEST_DESCRIPTION = ""
    TEST_CLAUSE = TEST @Value(VOTE_COUNT) CONTAINS_REGEX [0-9]
    BOOL_OP = OR
    PASSED -> AttributeCreator

Bookmark: Format attributes for pie chart and create HTML
Note: Format data for / Google's Chart API
AttributeCreator
    ATTR_TABLE = SET_TO _format_candidate = ['@Value(CANDIDATE)',@Value(VOTE_COUNT)]
    -> Aggregator
Note: Combine data by / voting district
Aggregator
    ACCUM_ATTRS_NAME = Merge Incoming Attributes
    GROUP_BY = LOCATION
    SEP = ,
    MODE = Attributes Only
    ORDERED = No
    CONCAT_ATTRS = _format_candidate
    AGGREGATE -> AttributeCreator_2
Note: Write HTML and / insert voting data
AttributeCreator_2
    ATTR_TABLE:
      SET_TO _html1 = <head>
            <script type="text/javascript" src="https://www.google.com/jsapi"></script>
            <script type="text/javascript">
              google.load("visualization", "1", {packages:["corechart"]});
              google.setOnLoadCallback(drawChart);
              function drawChart() {

              <!-- Define the Label and Data titles -->
               var data = google.visualization.arrayToDataTable([    ['Candidate', 'Votes'],

      SET_TO _html2 = @Value(_format_candidate)
      SET_TO _html3 = <!-- Close data tag -->
        ]);

        <!-- Set the chart type to Pie Chart -->
         var chart = new google.visualization.PieChart(document.getElementById('piechart'));

                 var options = {
                    <!-- Set Chart Title -->
                    title: 'Vancouver 2014 Municipal Election',

                    <!-- Generates 3D Pie Charts -->
                    is3D: true,

                    <!-- Aggregates Candidates with less than 10% total votes into 'Other' category -->
                    sliceVisibilityThreshold: .1,

                    <!-- Set Pie Chart size -->
                    'width':500,
                    'height':300

                  };

                 chart.draw(data, options);
        }
        </script>
        </head>

        <body>

            <!-- Set window size -->
            <div id="piechart" style="width: 450px; height: 300px;"></div>

          </body>
    -> StringConcatenator
Note: Join HTML attributes
StringConcatenator
    PARM_LINE = @Value(_html1)@Value(_html2)@Value(_html3)
    ACTION = Create New Attribute
    VAL_ATTR = _html
    -> FeatureMerger [SUPPLIER]

Bookmark: Create center points for pins
Note: Create voting disticts by dissolving / on local area boundaries
Dissolver
    GROUP_BY = LOCAL_AREA
    ACCUM_INPUT_ATTRS = Use Attributes From One Feature
    CONNECT_Z_MODE = First Wins
    DEAGGREGATE_INPUT = Yes
    NO_OVRLP = No
    AREA -> CenterPointReplacer
    AREA -> AttributeKeeper
Note: Create centroids for placemark pins
CenterPointReplacer
    MODE = Center Point
    POINT -> CoordinateExtractor
Note: Store coordinates as attributes
CoordinateExtractor
    X_ATTR = LONGITUDE
    IND = 0
    Y_ATTR = LATITUDE
    MODE = Specify Coordinate
    Z_ATTR = _z
    -> FeatureMerger [REQUESTOR]

Bookmark: Geographic output
Note: Select attribute for description
AttributeKeeper
    KEEP_ATTRS = LOCAL_AREA
    -> KMLPropertySetter
Note: Join election data and / coordinate information
FeatureMerger
    MERGE_TYPE = Attributes and Geometry
    PROCESS_DUPS = No
    IGNORE_NULLS = No
    REJECT_NULL_MISSING_KEYS = No
    ATTR_CONFLICT_RES = Use Requestor
    ATTR_ACCUM_MODE = Merge Supplier
    SUPPLIERS_FIRST = No
    JOIN_KEYS = @Value(LOCAL_AREA) @Value(LOCATION) AUTO
    MERGED -> Reprojector
Note: Reproject to WGS84
Reprojector
    DEST = LL-WGS84
    INTERPOLATION_TYPE_NAME = Nearest Neighbor
    SOURCE = Read from feature
    RASTER_CELL_SIZE = Preserve Cells
    REPROJECTED -> KMLPropertySetter_2

Bookmark: Style the KML
Note: KMLPropertySetter: Configures the / placemarks, and name, summary, / title for description balloons
KMLPropertySetter
    TESSELATE = Yes
    NAME = @Value(LOCAL_AREA)
    EXTRUDE = No
    CONTENT = Voting District
    ADD_ATTR_TABLE = No
    CONTENT_TYPE = Text
    SUMMARY = @Value(LOCAL_AREA) Voting District
    VISIBILITY = Yes
    GEOM_TYPE = Vector
    -> KMLStyler
KMLStyler
    ICON_OPACITY = 1.0
    LINE_WIDTH_UNITS = Pixels (Display Units)
    LABEL_SCALE = 1.0
    FILL_COLOR = 1,0.666667,0
    ICON_SCALE = 0.8
    STYLE_PER_FEATURE = Yes
    OPACITY = 1.0
    COLOR = 1,0.666667,0
    LABEL_VISIBILITY = Yes
    LABEL_OPACITY = 1.0
    FILL_OPACITY = 0.4
    LINE_WIDTH = 1.0
    KMLStyled -> Elections (writer OGCKML_1)
KMLPropertySetter_2
    TESSELATE = Yes
    NAME = @Value(LOCAL_AREA)
    EXTRUDE = No
    CONTENT = @Value(_html)
    ADD_ATTR_TABLE = No
    CONTENT_TYPE = HTML
    SUMMARY = Vancouver 2014 Election Results for @Value(LOCATION) District
    VISIBILITY = Yes
    GEOM_TYPE = Vector
    -> Elections (writer OGCKML_1)
