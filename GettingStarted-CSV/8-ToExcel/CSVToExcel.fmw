FME workspace CSVToExcel.fmw

Parameters:
- SourceDataset_CSV2 = C:\FMEData2017\ArticleData\CellSignal-Small.csv   # Source CSV (Comma Separated Value) File(s)
- DestDataset_XLSXW = $(FME_MF_DIR)CellSignals.xlsx   # Destination Microsoft Excel File

Readers:
- CSV2_1: CSV2 from $(SourceDataset_CSV2)

Writers:
- XLSXW_1: XLSXW to $(DestDataset_XLSXW)

Note: CSV: CellSignal-Small [CSV2]
CSV (reader CSV2_1)
    attributes: longitude string, latitude string, StationID string, Power string, Quality string, num_measures string, Code string, record_tstamp string
    -> DateTimeConverter
Note: Convert the date and time / From: 8/11/2017 8:58 / Using: %e/%N/%Y %k:%M / To: 2017-11-08 / Using: %Y-%m-%d
DateTimeConverter
    DATETIME_ATTR = record_tstamp
    REPAIR_INPUT = NO
    IN_FORMAT = %e/%N/%Y %k:%M
    OUT_FORMAT = %Y-%m-%d
    -> AttributeSplitter
Note: Split attributes using 3s15s
AttributeSplitter
    LIST_NAME = _list
    ATTR_NAME = Code
    DELIMITER = 3s15s
    DROP_EMPTY_PARTS = No
    TRIM_OPTION = Both
    -> AttributeManager
Note: Create attributes ID and give it the value of _list{0} / Create attribute Number and give it the value of _list{1}
AttributeManager
    ATTR_TABLE:
      SET_TO ID = @Value(_list{0})
      SET_TO Number = @Value(_list{1})
    -> CSV (writer XLSXW_1)
Note: : CellSignals [XLSXW]
CSV (writer XLSXW_1)
    attributes: longitude string(20), latitude string(20), StationID string(20), Power number(20), Quality number(20), num_measures string(20), Code string(20), record_tstamp time(20), ID string(20), Number number(20)
