FME workspace ToCSV.fmw

Parameters:
- SourceDataset_ESRISHAPE = ""C:\FMEData2017\Data\Transit\rapid_transit_line.shp" "C:\FMEData2017\Data\Transit\rapid_transit_stations.shp""   # Source Esri Shapefile(s)
- DestDataset_CSV2 = C:\Users\lsanderson\Documents\SafeProjects\GettingStarted-CSV   # Destination CSV (Comma Separated Value) Folder
- SourceDataset_OGCKML = C:\FMEData2017\Data\Boundaries\VancouverNeighborhoods.kml   # Source Google KML File or URL
- DestDataset_CSV2_3 = C:\Users\lsanderson\Documents\SafeProjects\GettingStarted-CSV   # Destination CSV (Comma Separated Value) Folder

Readers:
- ESRISHAPE_1: ESRISHAPE from $(SourceDataset_ESRISHAPE)
- OGCKML_1: OGCKML from $(SourceDataset_OGCKML)

Writers:
- CSV2_1: CSV2 to $(DestDataset_CSV2)
- CSV2_2: CSV2 to $(DestDataset_CSV2_3)

rapid_transit_line (reader ESRISHAPE_1) [off]
    attributes: LINE char(30)
    -> CoordinateExtractor
CoordinateExtractor [off]
    LIST_NAME = _indices
    MODE = All Coordinates
    -> ListExploder
ListExploder [off]
    ATTR_ACCUM_MODE = Merge List Attributes
    LIST_ATTR = _indices{}
    ATTR_CONFLICT_RES = Use List Attribute Values
    INDEX_ATTR = _element_index
    ELEMENTS -> AttributeManager
AttributeManager [off]
    ATTR_TABLE:
      REMOVE z
      REMOVE _element_index
    -> rapid_transit_line (writer CSV2_1)
rapid_transit_line (writer CSV2_1) [off]
    attributes: LINE string, x string, y string
rapid_transit_stations (reader ESRISHAPE_1) [off]
    attributes: STATION char(30)
    -> CoordinateExtractor_2
CoordinateExtractor_2 [off]
    LIST_NAME = _indices
    MODE = All Coordinates
    -> ListExploder_2
ListExploder_2 [off]
    ATTR_ACCUM_MODE = Merge List Attributes
    LIST_ATTR = _indices{}
    ATTR_CONFLICT_RES = Use List Attribute Values
    INDEX_ATTR = _element_index
    ELEMENTS -> AttributeManager_2
AttributeManager_2 [off]
    ATTR_TABLE:
      REMOVE z
      REMOVE _element_index
    -> rapid_transit_stations (writer CSV2_1)
    -> AttributeManager_2_Output
rapid_transit_stations (writer CSV2_1) [off]
    attributes: STATION string, x string, y string
AttributeManager_2_Output: Inspector [off]
Neighborhoods (reader OGCKML_1)
    attributes: NeighborhoodId kml_buffer, NeighborhoodName kml_buffer, NeighborhoodURL kml_buffer, TotalPopulation2001 kml_buffer, TotalPopulation2011 kml_buffer
    -> CoordinateExtractor_3
CoordinateExtractor_3
    LIST_NAME = _indices
    MODE = All Coordinates
    -> ListExploder_3
ListExploder_3
    ATTR_ACCUM_MODE = Merge List Attributes
    LIST_ATTR = _indices{}
    ATTR_CONFLICT_RES = Use List Attribute Values
    INDEX_ATTR = _element_index
    ELEMENTS -> AttributeManager_3
AttributeManager_3
    ATTR_TABLE:
      REMOVE NeighborhoodId
      REMOVE NeighborhoodURL
      REMOVE TotalPopulation2001
      REMOVE TotalPopulation2011
      REMOVE z
      REMOVE _element_index
    -> Neighborhoods (writer CSV2_2)
Neighborhoods (writer CSV2_2)
    attributes: NeighborhoodName string, x string, y string
