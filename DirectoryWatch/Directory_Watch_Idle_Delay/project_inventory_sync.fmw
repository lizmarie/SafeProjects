FME workspace project_inventory_sync.fmw

Parameters:
- Seconds = 300   # Seconds to Wait
- TEXT = token   # GoogleToken Enter your Google Fusion Table Refresh Token

Readers:
- GOOGLEFUSIONTABLES_DB_1: GOOGLEFUSIONTABLES_DB

Writers:
- GOOGLEFUSIONTABLES_DB_2: GOOGLEFUSIONTABLES_DB

Note: Workspace #3: / This workspace is used to check the Google Fusion Table project_inventory_file_status for modified files and then send them to be processed. If "updated" is set to false, the workspace will run, as well as run project_inventory_map.fmw and then set "updated" to true once complete. / Tasks: / 1) Paste your Google Fusion Table Refresh Token in to the user parameter $(GoogleToken) / 2) Connect to your FME Server in the FMEServerJobSubmitter and select the respository that the workspaces have been uploaded to, and select project_inventory_map.fmw. Then click the refresh icon in the lower left corner to bring in the parameters. / 3) Upload to FME Server and register with the Job Submitter
Note: project_inventory_file_status: [GOOGLEFUSIONTABLES_DB] / Enter your Google Fusion Refresh Token in the User Parameter $(GoogleToken)
project_inventory_file_status (reader GOOGLEFUSIONTABLES_DB_1)
    attributes: file_path text, last_modify_date text, updated text
    -> TimeStamper
Note: project_inventory_file_status: [GOOGLEFUSIONTABLES_DB]
project_inventory_file_status (writer GOOGLEFUSIONTABLES_DB_2)
    attributes: file_path text, last_modify_date text, updated text
Terminator
    MESSAGE = Translation Terminated

Bookmark: Test the idle time against current time for each Record
TimeStamper
    TIME_ATTR = _timestamp
    FMT = ^s
    -> Tester
Tester
    TEST_CLAUSE = TEST @Value(_timestamp) > @Evaluate(@Value(last_modify_date) + $(Seconds))
    TEST_DESCRIPTION = ""
    BOOL_OP = OR
    TEST_MODE = Automatic
    PASSED -> AttributeCreator

Bookmark: Format FilePath
AttributeCreator
    ATTR_TABLE = SET_TO source_data_path = @Value(file_path)
    -> StringReplacer
StringReplacer
    FIND_TEXT = file:////
    NO_MATCH = _FME_NO_OP_
    SRC_ATTRS = source_data_path
    REGEXP = NO
    CASE = NO
    REPLACE_TEXT = \\
    -> StringReplacer_2
StringReplacer_2
    FIND_TEXT = /
    NO_MATCH = _FME_NO_OP_
    SRC_ATTRS = source_data_path
    REGEXP = NO
    CASE = NO
    REPLACE_TEXT = \
    -> FMEServerJobSubmitter

Bookmark: Backup Data
Note: Add the connection to your FMEServer, select the repository that you have uploaded your workspaces. Then select project_inventory_map.fmw
FMEServerJobSubmitter
    USERNAME = admin
    PASSWORD =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
    PROCESSING_MODE = In Sequence
    SERVER_NAME = localhost
    WORKSPACE_NAME = project_inventory_to_map.fmw
    REPOSITORY = DWNew
    BLOCKING = Yes
    WORKSPACE_PARAMETERS = SourceDataset_XLSXR list \\KC-LS-WINDOWS1\DW_Resources\Project Inventory.xlsx GoogleToken string 1/FD4bwTWolDX_iEdzT591KuwGciT5J55dJ1aoZ68geIk
    PRIORITY = 100
    JOB_SUCCEEDED -> StringReplacer_3
    <REJECTED> -> Terminator

Bookmark: Update Tracking Database
StringReplacer_3
    FIND_TEXT = \
    NO_MATCH = _FME_NO_OP_
    SRC_ATTRS = file_path
    REGEXP = NO
    CASE = NO
    REPLACE_TEXT = \\
    -> AttributeCreator_2
AttributeCreator_2
    ATTR_TABLE:
      SET_TO fme_db_operation = update
      SET_TO fme_where = file_path = '@Value(file_path)'
    -> project_inventory_file_status (writer GOOGLEFUSIONTABLES_DB_2)
