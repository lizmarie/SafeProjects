FME workspace project_inventory_to_map.fmw

Parameters:
- MULTIFILE = \\KC-LS-WINDOWS1\DW_Resources\Project Inventory.xlsx
- TEXT = token   # GoogleToken Enter your Google Fusion Table Refresh Token

Readers:
- XLSXR_1: XLSXR from $(SourceDataset_XLSXR)

Writers:
- GOOGLEFUSIONTABLES_1: GOOGLEFUSIONTABLES

Note: Workspace #1: / This workspace takes an excel file called Project Inventory, creates points from Latitude and Longitude values, checks the ID on the spreadsheet to see if a new value has been added then writes to the Google Fusion Table called Project Inventory. / Tasks: / 1) Change user parameter $(SourceDataset_XLSXR) to point to your shared resource folder UNC path / 3) In the SQLExecutor, click Parameters and enter your Google Log In information to aquire a Google Fusion Table Refresh Token. Copy this Refresh Token for later use. / 3) Paste the Refresh Token in the user parameter $(GoogleToken), this will update the Refresh Token in both the SQLExecutor and the Google Fusion Table Writer / 4) Upload to your FME Server as a Job Submitter, ensure that you do not upload the excel file.
Note: Sheet1: Project Inventory [XLSXR] / Enter your Shared Folder UNC Path in the User Parameter $(SourceDataset_XLSXR)
Sheet1 (reader XLSXR_1)
    attributes: id time, Category char(9), project description char(23), latitude number(10,7), longitude number(12,7)
    -> CoordinateSystemSetter
Note: Project Inventory: [GOOGLEFUSIONTABLES] / Enter your Google Fusion Refresh Token in the User Parameter $(GoogleToken)
Project Inventory (writer GOOGLEFUSIONTABLES_1)
    attributes: id text, Category text, project description text

Bookmark: Create Coordinate System and Geometery
CoordinateSystemSetter
    COORDSYS = EPSG:4326
    -> VertexCreator
VertexCreator
    MODE_NAME = Add Point
    XVAL = @Value(longitude)
    YVAL = @Value(latitude)
    -> SQLExecutor [INITIATOR]

Bookmark: Upsert logic
Note: In the parameters, sign into Google to obtain a Google Fusion Table Refresh Token. Copy this token for use in other workspaces.
SQLExecutor
    COMBINE_ATTRS = Result Attributes Only
    SQL_STATEMENT:
      SELECT * FROM 'Project Inventory'
      WHERE id = '@Value(id)'
    FORMAT = GOOGLEFUSIONTABLES
    COMBINE_GEOM = Initiator Geometry Only
    GOOGLEFUSIONTABLES_REFRESH_TOKEN = token
    INITIATOR -> Tester_2
Tester_2
    TEST_CLAUSE = TEST @Value(_matched_records) > 0
    TEST_DESCRIPTION = ""
    TEST_MODE = Automatic
    BOOL_OP = OR
    PASSED -> AttributeCreator_2
    FAILED -> AttributeCreator_3
AttributeCreator_2
    ATTR_TABLE:
      SET_TO fme_db_operation = update
      SET_TO fme_where = id = '@Value(id)'
    -> Project Inventory (writer GOOGLEFUSIONTABLES_1)
AttributeCreator_3
    ATTR_TABLE = SET_TO fme_db_operation = insert
    -> Project Inventory (writer GOOGLEFUSIONTABLES_1)
