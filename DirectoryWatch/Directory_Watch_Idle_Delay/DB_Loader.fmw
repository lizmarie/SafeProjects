FME workspace DB_Loader.fmw
Title: DB_Loader

Parameters:
- SourceDataset_XLSXR = \\KC-LS-WINDOWS1\DW_Resources\Project Inventory.xlsx   # Source Microsoft Excel File(s)
- SourceDataset_CSV = $(FME_MF_DIR)project_inventory_file_status.csv   # Source CSV (CommaSeparatedValue) File(s)
- TEXT = token   # GoogleToken Enter your Google Fusion Table Refresh Token

Readers:
- XLSXR_1: XLSXR from $(SourceDataset_XLSXR)
- CSV2_1: CSV2 from $(SourceDataset_CSV)

Writers:
- GOOGLEFUSIONTABLES_1: GOOGLEFUSIONTABLES
- GOOGLEFUSIONTABLES_DB_1: GOOGLEFUSIONTABLES_DB

Note: Workspace #4: / This workspace creates two Google Fusion Tables in your Google account. The first table is the replica of Project Inventory.xlsx and will be updated when changes are made to the desktop version / The second table is the project_inventory_file_status which will be updated everytime the modify trigger was activated. This is created from the schema in a CSV file / Tasks: / 1) Update the $(SourceDataset_XLSXR) to point to the excel file in the shared Resources folder / 2) Update the $(SourceDataset_CSV) to the project_inventory_file_status.csv that was downloaded with this tutorial. / 3) Update the user parameter $(GoogleToken) to point to your Google Fusion Table Refresh Token / 4) Run the workspace / 5) Check your Google Drive to ensure the two tables were created
Note: Sheet1: Project Inventory [XLSXR]
Sheet1 (reader XLSXR_1)
    attributes: id time, Category char(9), project description char(23), longitude x_coordinate, latitude y_coordinate
    -> CoordinateSystemSetter
CoordinateSystemSetter
    COORDSYS = EPSG:4326
    -> VertexCreator
VertexCreator
    MODE_NAME = Add Point
    YVAL = @Value(latitude)
    XVAL = @Value(longitude)
    -> Project Inventory (writer GOOGLEFUSIONTABLES_1)
Note: Project Inventory: [GOOGLEFUSIONTABLES] / Enter your Google Fusion Refresh Token in the User Parameter $(GoogleToken)
Project Inventory (writer GOOGLEFUSIONTABLES_1)
    attributes: id text, Category text, project description text
Note: CSV: project_inventory_file_status [CSV2]
CSV (reader CSV2_1)
    attributes: file_path string, last_modify_date string, updated string, Date string
    -> project_inventory_file_status (writer GOOGLEFUSIONTABLES_DB_1)
Note: project_inventory_file_status: [GOOGLEFUSIONTABLES_DB]
project_inventory_file_status (writer GOOGLEFUSIONTABLES_DB_1)
    attributes: file_path text, last_modify_date text, updated text
