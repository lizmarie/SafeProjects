FME workspace project_inventory_status.fmw

Parameters:
- SourceDataset_DIRECTORY_WATCH_READER = $(FME_MF_DIR)sample_directory_watch.json.txt   # Source Text File(s)
- GoogleToken = token

Readers:
- DIRECTORY_WATCH_READER_1: DIRECTORY_WATCH_READER from $(SourceDataset_DIRECTORY_WATCH_READER)

Writers:
- GOOGLEFUSIONTABLES_DB_1: GOOGLEFUSIONTABLES_DB

Note: Workspace #2: / This workspace utilizes the Directory Watch Reader and runs when a Modify trigger is sent by the Directory Watch protocol. Information from the notification message are then stored in a Google Fusion Table called project_inventory_file_status. / Tasks: / 1) In the user parameter $(GoogleToken) paste your Refresh Token, this will update the Refresh Token for both the SQLExecutor and the Google Fusion Table Writer / 2) Upload to FME Server and register to the Notification Service, subcribe to the sync_tool topic and select Source Text File(s). / 3) In FME Server upload the Direcotry Watch Reader
Note: DirectoryWatcher: sample_directory_watch [DIRECTORY_WATCH_READER] / Upload the DIRECTORY_WATCH_READER.fds into your FME Server, Resources > Engine > Formats
DirectoryWatcher (reader DIRECTORY_WATCH_READER_1)
    attributes: fns_type char(20), dirwatch_file_operation char(12), dirwatch_file_name char(256)
    -> FilenamePartExtractor
FilenamePartExtractor
    FULLNAME_ATTR = _filename
    DIRNAME_ATTR = _dirname
    EXTENSION_ATTR = _extension
    DIRPATH_ATTR = _dirpath
    SRC_ATTR = @Value(dirwatch_file_name)
    ROOTNAME_ATTR = _rootname
    -> Tester
Tester
    TEST_MODE = Automatic
    BOOL_OP = AND
    TEST_CLAUSE:
      TEST @Value(dirwatch_file_operation) = ENTRY_MODIFY
      TEST @Value(_extension) = xlsx
      TEST @Value(dirwatch_file_operation) NOT_CONTAINS ~$
    TEST_DESCRIPTION = ""
    PASSED -> StringReplacer
StringReplacer
    REGEXP = NO
    REPLACE_TEXT = \\
    SRC_ATTRS = dirwatch_file_name
    FIND_TEXT = \
    NO_MATCH = _FME_NO_OP_
    CASE = NO
    -> SQLExecutor [INITIATOR]
TimeStamper
    FMT = ^s
    TIME_ATTR = _timestamp
    -> AttributeCopier
AttributeCopier
    ATTR_TABLE:
      COPY dirwatch_file_name > file_path
      COPY _timestamp > last_modify_date
    -> project_inventory_file_status (writer GOOGLEFUSIONTABLES_DB_1)
Note: project_inventory_file_status: [GOOGLEFUSIONTABLES_DB] / Enter your Google Fusion Refresh Token in the User Parameter $(GoogleToken)
project_inventory_file_status (writer GOOGLEFUSIONTABLES_DB_1)
    attributes: file_path text, last_modify_date text, updated text

Bookmark: Upsert logic
Note: Uses the Google Fusion Table Refresh Token, which is modified with the User Parameter $(GoogleToken)
SQLExecutor
    COMBINE_ATTRS = Result Attributes Only
    SQL_STATEMENT:
      SELECT *
      FROM project_inventory_file_status
      WHERE file_path = '@Value(dirwatch_file_name)'
    FORMAT = GOOGLEFUSIONTABLES_DB
    COMBINE_GEOM = Initiator Geometry Only
    GOOGLEFUSIONTABLES_DB_REFRESH_TOKEN = $(GoogleToken)
    INITIATOR -> Tester_2
Tester_2
    TEST_MODE = Automatic
    BOOL_OP = OR
    TEST_CLAUSE = TEST @Value(_matched_records) > 0
    TEST_DESCRIPTION = ""
    PASSED -> AttributeCreator_2
    FAILED -> AttributeCreator_3
AttributeCreator_2
    ATTR_TABLE:
      SET_TO fme_db_operation = update
      SET_TO fme_where = file_path = '@Value(dirwatch_file_name)'
    -> TimeStamper
AttributeCreator_3
    ATTR_TABLE = SET_TO fme_db_operation = insert
    -> TimeStamper
