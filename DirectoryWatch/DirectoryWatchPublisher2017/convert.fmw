FME workspace convert.fmw

Parameters:
- TEXT = token   # ServerToken Enter your FMEServer Token
- TEXT = email   # Email Enter the email you wish to receive updates to
- HostName = localhost   # Enter the name of your Host
- DestDataset_TEXTLINE = /tmp/outfile.txt   # Destination Text File
- SourceDataset_TEXTLINE = /tmp/somefile.txt   # Source Text File(s)
- FME_SHAREDRESOURCE_TEMP = .

Readers:
- TEXTLINE_1: TEXTLINE from $(SourceDataset_TEXTLINE)

Writers:
- TEXTLINE_2: TEXTLINE to $(DestDataset_TEXTLINE)

Note: Tasks: / 1) Enter your FME Server connection into the FMEServerJobSubmitter, select the Samples Repository and select the easyTranslation2.fmw workspace / 2) Publish to FME Server Samples Repository, select the Notification Service, click edit. For Topics to Subscribe add convert_tool, then for Parameter to Get Topic Message select Source Text Fiile(s) / 3) For Email: Set up the User Parameters with your FME Server Token, the email you would like to recieve the conversion and your FME Server Host Name / 4) Publish to FME Server, edit the Notifications Service and for Notifiy on Job Completion Post to Topics select email_results, and for Post Data From select Destination Text File
Note: AttributeCreator_3 [AttributeCreator] / Attributes To Set: / Attribute Name / Value / output_format / SHAPE / source_format / ACAD
AttributeCreator_3
    ATTR_TABLE:
      SET_TO output_format = SHAPE
      SET_TO source_format = ACAD
    -> FMEServerJobSubmitter
Note: Perform the actual conversion / using the easy translator / Connect to your FME Server, connect to the Samples Respository and the easyTranslation2.fmw workspace.
Note: To set up the emailer, enter your FME Server Token, the email you would like to send the email to and the name of your FME Server Host.
FMEServerJobSubmitter
    PRIORITY = 100
    WORKSPACE_PARAMETERS = SourceDataset_GENERIC list @Value(source_path) SourceFormat string @Value(source_format) COORDSYS string  DestinationFormat string @Value(output_format) COORDSYS_Dest string  DestDataset_GENERIC string $(FME_SHAREDRESOURCE_TEMP)/convert_tool/output/@Value(_rootname).zip GENERIC_OUT_BASE_NAME_GENERIC string translated_data
    BLOCKING = Yes
    PROCESSING_MODE = In Sequence
    WORKSPACE_NAME = easyTranslator2.fmw
    SERVER_CONNECTION = Server Demo
    REPOSITORY = Samples
    JOB_SUCCEEDED -> AttributeCreator_2
    JOB_FAILED -> FMEServerEmailGenerator_2

Bookmark: Find a file to process
text_line (reader TEXTLINE_1)
    attributes: text_line_data buffer
    -> JSONFlattener
JSONFlattener
    NEW_ATTRIBUTES = "dirwatch_publisher_content fns_type "
    JSON_DOCUMENT = @Value(text_line_data)
    ERROR_LIST_ATTR = _json_error
    RECURSIVE = Yes
    -> Tester
Note: Only process new files
Tester
    TEST_MODE = Automatic
    TEST_CLAUSE = TEST @Value(dirwatch_publisher_content) CONTAINS ENTRY_CREATE
    BOOL_OP = AND
    TEST_DESCRIPTION = ""
    PASSED -> AttributeCopier
    FAILED -> Terminator
AttributeCopier
    ATTR_TABLE = COPY dirwatch_publisher_content > source_path
    -> StringReplacer
StringReplacer
    SRC_ATTRS = source_path
    FIND_TEXT = "ENTRY_CREATE "
    REGEXP = NO
    CASE = NO
    NO_MATCH = _FME_NO_OP_
    -> FilenamePartExtractor_2
FilenamePartExtractor_2
    SRC_ATTR = @Value(source_path)
    DIRPATH_ATTR = _dirpath
    EXTENSION_ATTR = _extension
    DIRNAME_ATTR = _dirname
    FULLNAME_ATTR = _filename
    ROOTNAME_ATTR = _rootname
    -> AttributeCreator_3
Terminator
    MESSAGE = Translation Terminated

Bookmark: Emailer
Note: Creates a download link for the file and sends it to an email provided in the User Parameters
AttributeCreator_2 [off]
    ATTR_TABLE = SET_TO download_link = $(HostName)/fmerest/v3/resources/connections/FME_SHAREDRESOURCE_TEMP/filesys/convert_tool/output/@Value(_rootname).zip?accept=contents&token=$(ServerToken)
    -> FMEServerEmailGenerator [off]
text_line (writer TEXTLINE_2) [off]
    attributes: text_line_data buffer

Bookmark: Sucess Emailer
FMEServerEmailGenerator [off]
    email_to = $(Email)
    email_subscriber_content:
      <div><p>You're file is converted and you can get it here:</p>
      <p><a href="@Value(download_link)">@Value(_rootname).zip</a></p></div>
    email_subject = Conversion complete for @Value(_filename)
    -> text_line (writer TEXTLINE_2) [off]

Bookmark: Failure Emailer
FMEServerEmailGenerator_2 [off]
    email_to = $(Email)
    email_subscriber_content = OH NO!!! This file failed to convert: @Value(_filename) Please see job logs for error messages
    email_subject = Conversion Failed for @Value(_filename)
    -> text_line (writer TEXTLINE_2) [off]

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.

Parameters:
- email_to =   # To
- email_cc =   # CC
- email_from =   # From
- email_replyto =   # Reply to
- email_subject =   # Subject
- email_subscriber_content =   # Message
- email_attachment_paths =   # Attachments (comma separated)

INPUT (input)
    -> Counter
Counter
    DOMAIN = counter
    START = 0
    SCOPE = Local
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    ATTR_LIST = _email_to,$(email_to),_email_subject,$(email_subject),_email_subscriber_content,$(email_subscriber_content)
    NUM_SUBSEQUENT_FEATURES = 0
    -> JSONTemplater [ROOT]
JSONTemplater
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    CONSECUTIVE_GROUPS = No
    VISIBLE_QUERY_VALIDATE = Yes
    RESULT_ATTRIBUTE = text_line_data
    -> Tester
Tester
    TEST_MODE = Automatic
    TEST_CLAUSE = TEST _email_attachment_paths ATTRIBUTE_IS_EMPTY <Unused>
    BOOL_OP = OR
    TEST_DESCRIPTION = ""
    PASSED -> OUTPUT (output)
    FAILED -> AttributeSplitter
OUTPUT (output)

Bookmark: Add the attachments
AttributeSplitter
    DELIMITER = ,
    TRIM_OPTION = Both
    DROP_EMPTY_PARTS = No
    LIST_NAME = _email_attachment_path_list
    ATTR_NAME = _email_attachment_paths
    -> ListExploder
ListExploder
    INDEX_ATTR = _element_index
    LIST_ATTR = _email_attachment_path_list{}
    MODE = List Elements and Original Attributes
    LIST_FOUND -> StringConcatenator
StringConcatenator
    PARM_LINE = "email_attachment{@Value(_element_index)}": "@Value(_email_attachment_path_list)"
    VAL_ATTR = _email_attachment_json
    -> Aggregator
Aggregator
    SEP = ,
    ACCUM_ATTRS_NAME = Yes
    GROUP_BY = _email_feature_id
    ORDERED = No
    AGGREGATE_TYPE = Homogeneous Collection (If Possible)
    MODE = Assemble One Level
    CONCAT_ATTRS = _email_attachment_json
    AGGREGATE -> StringReplacer_2
StringReplacer_2
    SRC_ATTRS = _email_attachment_json
    FIND_TEXT = \
    REGEXP = no
    CASE = no
    REPLACE_TEXT = \\
    NO_MATCH = _FME_NO_OP_
    -> StringReplacer
StringReplacer
    SRC_ATTRS = text_line_data
    FIND_TEXT = }
    REGEXP = no
    CASE = no
    REPLACE_TEXT:
      ,
      @Value(_email_attachment_json)
      }
    NO_MATCH = _FME_NO_OP_
    -> OUTPUT (output)
