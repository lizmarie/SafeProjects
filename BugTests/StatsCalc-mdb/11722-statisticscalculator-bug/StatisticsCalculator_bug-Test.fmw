FME workspace StatisticsCalculator_bug-Test.fmw

Parameters:
- SourceDataset_MDB_ADO = $(FME_MF_DIR)ep.mdb   # Database Path
- SourceDataset_XLSXR = $(FME_MF_DIR)TestData\test2.xlsx   # Source Microsoft Excel File(s)
- SourceDataset_MDB_ADO_5 = $(FME_MF_DIR)TestData\test2.mdb   # Database Path
- SourceDataset_MDB_ADO_7 = $(FME_MF_DIR)TestData\statstest.mdb   # Database Path
- SourceDataset_XLSXR_3 = $(FME_MF_DIR)TestData\StatsTest.xlsx   # Source Microsoft Excel File(s)
- SourceDataset_MDB_ADO_6 = $(FME_MF_DIR)TestData\test3.mdb   # Database Path

Readers:
- MDB_ADO_1: MDB_ADO from $(SourceDataset_MDB_ADO)
- XLSXR_1: XLSXR from $(SourceDataset_XLSXR)
- MDB_ADO_2: MDB_ADO from $(SourceDataset_MDB_ADO_5)
- MDB_ADO_3: MDB_ADO from $(SourceDataset_MDB_ADO_7)
- XLSXR_2: XLSXR from $(SourceDataset_XLSXR_3)
- MDB_ADO_4: MDB_ADO from $(SourceDataset_MDB_ADO_6)

StatisticsCalculator
    COUNT_ATTR = _count
    STATS_ATTRS = pk_celda
    PREPEND_ATTR_NAME_CHOICE = For multiple results only
    GROUP_BY = pk_celda
    COMPUTE_HISTOGRAM = NO
    SUMMARY -> Inspector
Inspector
Note: FME 2017.1 / Build 17539 / Windows 32 bits / Inspector: 16.102 features / Inspecto_2: 17.891 features / In Inspector pk_celda=1 and _count=25, in Inspector_2 the same value (C1) has _count=5.
Note: Tested in 2016.1, 2017.1.1 and 2018.0 / Users data produces the results listed in the annotation above. User thought the bug might be with the StatisticsCalculator, but after thorough testing, it appears to be an issue with the users data. / I converted the users data into excel and back into ms access format and it worked as expected. I also created both .xlsx and .mdb files with randomly generated numbers to replicate the users data and it also worked as expected. / The only test I was able to reproduce their results was converting their data into another .mdb file.
StringConcatenator
    PARM_LINE = C@Value(pk_celda)
    ACTION = Overwrite Existing Attributes
    ATTRLIST = pk_celda
    -> StatisticsCalculator_2
StatisticsCalculator_2
    COUNT_ATTR = _count
    STATS_ATTRS = pk_celda
    PREPEND_ATTR_NAME_CHOICE = For multiple results only
    GROUP_BY = pk_celda
    COMPUTE_HISTOGRAM = NO
    SUMMARY -> Inspector_2
Inspector_2

Bookmark: Users Original Data
Note: especies: ep [MDB_ADO]
especies (reader MDB_ADO_1)
    attributes: pk_celda long, CodigoEspecie text(200), NombreCientifico text(200), NombreComun text(200)
    -> StatisticsCalculator
    -> StringConcatenator

Bookmark: Original .mdb to new .mdb
Note: especies: test3 [MDB_ADO]
especies (reader MDB_ADO_4) [off]
    attributes: pk_celda long, CodigoEspecie text(200), NombreCientifico text(200), NombreComun text(200)
    -> StatisticsCalculator
    -> StringConcatenator

Bookmark: Translated orginal data to .xlsx
Note: especies: test2 [XLSXR]
especies (reader XLSXR_1) [off]
    attributes: pk_celda number(5,0), CodigoEspecie char(7), NombreCientifico char(34), NombreComun char(45)
    -> StatisticsCalculator
    -> StringConcatenator

Bookmark: Translated .xlsx back into .mdb
Note: especies: test2 [MDB_ADO]
especies (reader MDB_ADO_2) [off]
    attributes: pk_celda decimal(5,0), CodigoEspecie text(7), NombreCientifico text(34), NombreComun text(45)
    -> StringConcatenator
    -> StatisticsCalculator

Bookmark: Randomly generated numbers to replicate user data
Note: test: statstest [MDB_ADO]
test (reader MDB_ADO_3) [off]
    attributes: StatCalcTest text(200), _random_number text(200), _random_number2 text(200)
    -> StringConcatenator
    -> StatisticsCalculator
Note: Sheet1: StatsTest [XLSXR]
Sheet1 (reader XLSXR_2) [off]
    attributes: StatCalcTest number(4,0), _random_number number(5,0), _random_number2 number(6,0)
    -> StringConcatenator
    -> StatisticsCalculator
