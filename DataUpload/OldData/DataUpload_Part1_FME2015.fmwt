FME workspace DataUpload_Part1_FME2015.fmwt
Title: 1_CheckFieldStatus

Readers:
- MITAB_1: MITAB from $(FME_MF_DIR)1/Data/Parks.tab
- CSV_1: CSV from $(FME_MF_DIR)1/Data/weekendplayfieldstatus.csv

Writers:
- OGCKML_1: OGCKML to C:\temp\Data Upload Tutorial\Output\FieldStatus.kml

Note: Read in park information
Parks (reader MITAB_1)
    attributes: ParkId smallint, RefParkId smallint, ParkName char(40), NeighborhoodName char(40), EWStreet char(30), NSStreet char(30), DogPark char(1), Washrooms char(1), SpecialFeatures char(1)
    -> FeatureMerger [input 1]
CSV (reader CSV_1)
    attributes: park_name char(30), park_id number(4,0), site_area char(15), closure_notes char(39), weekend_status char(16), last_updated char(12)
    -> FeatureMerger [input 2]
Note: Pull in current field availability / information from CSV
FeatureMerger
    ATTR_CONFLICT_RES = Use Requestor
    SUPPLIERS_FIRST = No
    JOIN_KEYS = @Value(ParkName) @Value(park_name) AUTO
    ATTR_ACCUM_MODE = Merge Supplier
    MERGE_TYPE = Attributes and Geometry
    PROCESS_DUPS = No
    MERGED -> KMLStyler
    NOT_MERGED -> KMLStyler_2
Note: Add park name labels and / include field availability in / KML description.
KMLPropertySetter
    CONTENT_TYPE = Text
    EXTRUDE = No
    ATTR_TABLE_TITLE = Attributes
    SUMMARY = Field Status: @Value(weekend_status)
    ADD_ATTR_TABLE = Yes
    TESSELATE = Yes
    GEOM_TYPE = Vector
    NAME = @Value(ParkName)
    VISIBILITY = Yes
    -> FieldStatus (writer OGCKML_1)
FieldStatus (writer OGCKML_1)
    attributes: ParkName kml_char(200), NeighborhoodName kml_char(200), EWStreet kml_char(200), NSStreet kml_char(200), Washrooms kml_char(200), SpecialFeatures kml_char(200), SiteArea kml_char(200), ClosureNotes kml_char(200), Status kml_char(200), LastUpdated kml_char(200)

Bookmark: Color parks depending on field availablility
KMLStyler
    FILL_COLOR = FME_CONDITIONAL:DEFAULT_VALUE'0,0.501961,0'BOOL_OP;OR;COMPOSITE_TEST;<Unused>;TEST @Value(weekend_status) = Closed'1,0,0'FME_NUM_CONDITIONS2___
    LABEL_OPACITY = 1.0
    LABEL_VISIBILITY = Yes
    LINE_WIDTH = 1.0
    FILL_OPACITY = 0.68
    ICON_SCALE = 0.8
    COLOR = FME_CONDITIONAL:DEFAULT_VALUE'0,0.501961,0'BOOL_OP;OR;COMPOSITE_TEST;<Unused>;TEST @Value(weekend_status) = Closed'1,0,0'FME_NUM_CONDITIONS2___
    STYLE_PER_FEATURE = Yes
    LABEL_SCALE = 1.0
    ICON_OPACITY = 1.0
    LINE_WIDTH_UNITS = Pixels (Display Units)
    OPACITY = 1.0
    KMLStyled -> NullAttributeMapper
KMLStyler_2
    FILL_COLOR = 0.602716,0.602716,0.602716
    LABEL_OPACITY = 1.0
    LABEL_VISIBILITY = Yes
    LINE_WIDTH = 1.0
    FILL_OPACITY = 0.58
    ICON_SCALE = 0.8
    COLOR = 0.2,0.2,0.2
    STYLE_PER_FEATURE = Yes
    LABEL_SCALE = 1.0
    ICON_OPACITY = 1.0
    LINE_WIDTH_UNITS = Pixels (Display Units)
    OPACITY = 1.0
    KMLStyled -> NullAttributeMapper

Bookmark: Clean up attributes
NullAttributeMapper
    NULL_TREATMENT = New Value
    ATTRLIST = park_name park_id site_area closure_notes weekend_status last_updated
    SOURCE_ATTR_VAL = Null "Missing (Selected Attributes Only)"
    NEW_VALUE = N/A
    ATTRCHOICE = Selected Attributes
    -> AttributeCopier
AttributeCopier
    ATTR_LIST = closure_notes,ClosureNotes,"",weekend_status,Status,"",site_area,SiteArea,"",last_updated,LastUpdated,""
    -> KMLPropertySetter
