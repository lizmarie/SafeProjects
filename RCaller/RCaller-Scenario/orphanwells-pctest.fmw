FME workspace orphanwells-pctest.fmw
Title: RCaller-Wells-Windows

Parameters:
- SourceDataset_XLSXR = $(FME_MF_DIR)AER_Licence_Details_Report.xlsx   # Source Microsoft Excel File(s)
- DestDataset_XLSXW = $(FME_MF_DIR)Inspect Oil Wells.xlsx   # Destination Microsoft Excel File
- SourceDataset_ESRISHAPE = $(FME_MF_DIR)V4-1_LSD.shp   # Source Esri Shapefile(s)
- DestDataset_ESRISHAPE = C:\Users\lsanderson\Downloads   # Destination Esri Shapefile Folder

Readers:
- XLSXR_1: XLSXR from $(SourceDataset_XLSXR)
- ESRISHAPE_1: ESRISHAPE from $(SourceDataset_ESRISHAPE) in LL84

Writers:
- XLSXW_1: XLSXW to $(DestDataset_XLSXW)
- ESRISHAPE_2: ESRISHAPE to $(DestDataset_ESRISHAPE)

Note: Well Licences: AER_Licence_Details_Report [XLSXR]
Well Licences (reader XLSXR_1)
    attributes: Company char(41), Licence Number char(7), Licence Status char(11), Surface Location char(15), UWI char(20), Field/Area Name char(17), Pool/Deposit Name char(22), Final Total Depth, m number(7,1), Last Volumetric Activity Date date, Last Annual Oil Prod, m³ number(6,1), Last Annual Gas Prod, 10³m³ number(8,1), Last Annual Water Prod, m³ number(8,1)
    -> AttributeRenamer
Note: AttributeRenamer [AttributeRenamer] / Attributes To Rename: Input AttributeOutput AttributeDefault ValueCompanyCompany<not set>Field/Area NameAreaName<not set>Final Total Depth, mTotalDepth<not set>Last Annual Gas Prod, 10³m³GasProduction<not set>Last Annual Oil Prod, m³OilProduction<not set>Last Annual Water Prod, m³WaterProduction<not set>Last Volumetric Activity DateActivityDate<not set>Licence NumberLicenceNumber<not set>Licence StatusLicenceStatus<not set>Pool/Deposit NameDepositName<not set>Surface LocationSurfaceLocation<not set>UWIUWI<not set>
Note: Note: This workspace will only run on windows. / To run on Mac/Linux change the file naming convention in the first Rcaller and the FeatureReader to: / RCaller - png(filename="/Users/YourUserName/Desktop/OrphanWells.png") / FeatureReader Dataset - /Users/YourUserName/Desktop/OrphanWells.png
AttributeRenamer
    ATTR_TABLE:
      RENAME_SET_DEFAULT Company
      RENAME_SET_DEFAULT Field/Area Name > AreaName
      RENAME_SET_DEFAULT Final Total Depth, m > TotalDepth
      RENAME_SET_DEFAULT Last Annual Gas Prod, 10³m³ > GasProduction
      RENAME_SET_DEFAULT Last Annual Oil Prod, m³ > OilProduction
      RENAME_SET_DEFAULT Last Annual Water Prod, m³ > WaterProduction
      RENAME_SET_DEFAULT Last Volumetric Activity Date > ActivityDate
      RENAME_SET_DEFAULT Licence Number > LicenceNumber
      RENAME_SET_DEFAULT Licence Status > LicenceStatus
      RENAME_SET_DEFAULT Pool/Deposit Name > DepositName
      RENAME_SET_DEFAULT Surface Location > SurfaceLocation
      RENAME_SET_DEFAULT UWI
    -> RCaller [wells]
    -> Tester
Note: V4-1_LSD: V4-1_LSD [ESRISHAPE]
V4-1_LSD (reader ESRISHAPE_1)
    attributes: PID char(15), FILE_NAME char(6), TRM char(6), M short, RGE short, TWP short, SEC short, QS char(2), LS short, DESCRIPTOR char(50), RA char(2)
    -> AttributeRemover
Note: Remove RA
AttributeRemover
    REMOVE_ATTRS = RA
    -> FeatureMerger [REQUESTOR]
Note: Merge the Well Licences with the LSD file. Matching attributes LS = LSD, leave everything else as the defaults
FeatureMerger
    PROCESS_DUPS = No
    ATTR_CONFLICT_RES = Use Requestor
    SUPPLIERS_FIRST = No
    ATTR_ACCUM_MODE = Merge Supplier
    MERGE_TYPE = Attributes Only
    IGNORE_NULLS = No
    REJECT_NULL_MISSING_KEYS = No
    JOIN_KEYS = @Value(M) @Value(M) AUTO @Value(RGE) @Value(RGE) AUTO @Value(SEC) @Value(SEC) AUTO @Value(TWP) @Value(TWP) AUTO @Value(LS) @Value(LSD) AUTO
    MERGED -> OrphanWells (writer ESRISHAPE_2)
Note: OrphanWells: Downloads [ESRISHAPE] / Geometry: shape_polygon
OrphanWells (writer ESRISHAPE_2)
    attributes: Company char(41), Licence_Nu char(7), Licence_St char(11), Surface_Lo char(15), UWI char(20), Field_Area char(17), Pool_Depos char(22), Final_Tota number(7,1), Last_Volum date, Last_Annua number(6,1), Last_Ann00 number(8,1), Last_Ann01 number(8,1)

Bookmark: Create a PNG of a Scatterplot
Note: Creates a png file then plots a scatterplot using the four variables in the input.
RCaller
    TABLE_DEF = wells,GasProduction,varchar(200),OilProduction,varchar(200),WaterProduction,varchar(200),TotalDepth,varchar(200)
    OUTPUT_SCHEMA = pathname
    QUERY_DEF:
      Output,#Add your inputs here by dragging in from the data frame list on the left.
      #Populate the columns of the fmeOutput data frame with your desired script output.
      #The columns of the fmeOutput Data frame will be converted to attributes on output features.
      #For example:
      #fmeOutput<-data.frame(numbers=c(1,2,3),letters=c('A','B','C'))
      png(filename="C:\\Users\\lsanderson\\Documents\\OrphanPlot.png")
      plot(wells)
      dev.off()
      fmeOutput<-data.frame(1),pathname
    -> FeatureReader [INITIATOR]
Note: PNG format
FeatureReader
    DATASET = C:\Users\lsanderson\Documents\OrphanPlot.png
    INTERACT = <No Spatial Filter>
    ATTR_ACCUM_MODE = Only Use Result
    PNGRASTER_USE_SEARCH_ENVELOPE = NO
    PNGRASTER_READER_META_ATTRIBUTES = fme_dataset fme_basename
    PNGRASTER_GROUP_BY_DATASET = No
    FORMAT = PNGRASTER
    OUTPUT_FEATURES_DISPLAY = Schema and Data Features
    COMBINE_GEOM = Use Result
    <OTHER> -> FeatureReader__Generic_
FeatureReader__Generic_: Inspector

Bookmark: Remove missing values and determine wells with low production
Note: Tests to see if OilProduction has a value. Null or missing values sent to the Failed output port
Tester
    TEST_CLAUSE = TEST @Value(OilProduction) ATTRIBUTE_HAS_VALUE ""
    TEST_MODE = Automatic
    BOOL_OP = OR
    TEST_DESCRIPTION = ""
    PASSED -> RCaller_2 [wells]
    FAILED -> Well Licences (writer XLSXW_1)
Note: R Script that removes Rows 2127-2133 which contain copy right information, that will affect our analysis. / Creates a new variable called TotalProduction which adds OilProduction, GasProduction and WaterProduction / Creates a new column in wells with TotalProduction / Aggregates the data based on AreaName and adds the TotalProduction for each area. / Finds all Areas with a combined TotalProduction less than 10 and puts it into a new variable called Remove / The data frame then outputs Remove.
RCaller_2
    TABLE_DEF = wells,Company,varchar(41),AreaName,varchar(200),TotalDepth,varchar(200),GasProduction,"real(200,10)",OilProduction,"real(200,10)",WaterProduction,"real(200,10)",ActivityDate,varchar(200),LicenceNumber,varchar(200),LicenceStatus,varchar(200),DepositName,varchar(200),SurfaceLocation,varchar(200),UWI,varchar(20)
    OUTPUT_SCHEMA = AreaName Company SurfaceLocation TotalDepth GasProduction OilProduction WaterProduction TotalProduction
    QUERY_DEF:
      Output,#Add your inputs here by dragging in from the data frame list on the left.
      #Populate the columns of the fmeOutput data frame with your desired script output.
      #The columns of the fmeOutput Data frame will be converted to attributes on output features.
      #For example:
      #fmeOutput<-data.frame(numbers=c(1,2,3),letters=c('A','B','C'))
      wells <- wells[-c(2127:2133, drop=FALSE),]

      TotalProduction <- wells$OilProduction +  wells$GasProduction + wells$WaterProduction
      wells$TotalProduction <- TotalProduction
      listFieldName <- aggregate(wells$TotalProduction, by=list(FieldName=wells$AreaName), FUN=sum)
      Remove <- wells[wells$TotalProduction < 10,]
      fmeOutput<-data.frame(Remove)

      ,AreaName Company SurfaceLocation TotalDepth GasProduction OilProduction WaterProduction TotalProduction
    -> Sorter
    -> RCaller_2_Output
RCaller_2_Output: Inspector [off]
Note: Optional: Sorts by AreaName and then by TotalProduction to cluser areas together
Sorter
    SORT_PARM = AreaName ALPHA ASCENDING TotalProduction NUMERIC DESCENDING
    SORTED -> AttributeSplitter
Note: Well Licences: Inspect Oil Wells [XLSXW] / Null or missing values written to an Excel File to review later
Well Licences (writer XLSXW_1)
    attributes: Company string(41), Licence Number string(7), Licence Status string(11), Surface Location string(15), UWI string(20), Field/Area Name string(17), Pool/Deposit Name string(22), Final Total Depth, m number(7), Last Volumetric Activity Date date(20), Last Annual Oil Prod, m³ number(6), Last Annual Gas Prod, 10³m³ number(8), Last Annual Water Prod, m³ number(8)

Bookmark: Extract LSD, SEC, TWP, RGE and M from SurfaceLocation
Note: Splits SurafaceLocation into its individual parts by the delimeter - / Creates _list{}, which contains LSD, SEC, TWP, RGE, and M (unlabled) / To reveal the individual list parts, right click on _list{} and click Expose Elements, then Select Elements from _list{} enter 0-3
AttributeSplitter
    DELIMITER = -
    LIST_NAME = _list
    ATTR_NAME = SurfaceLocation
    TRIM_OPTION = Both
    DROP_EMPTY_PARTS = No
    -> SubstringExtractor
Note: RGE and M were not seperated by the delimeter, so they need to be extracted. / Extract RGE by the Start Index of 0 and the End Index of 1. For the Result Attribute call it RGE
SubstringExtractor
    START = 0
    RESULT_ATTR = RGE
    END = 1
    SRC_STRING = @Value(_list{3})
    -> SubstringExtractor_2
Note: For M (Meridian), it has a coordinate direction associated with it, since we are only working with Alberta data we do not require this. Extract only the number by a Start Index of 3 and an End Index of 3. For the Result Attribute call it M
SubstringExtractor_2
    START = 3
    RESULT_ATTR = M
    END = 3
    SRC_STRING = @Value(_list{3})
    -> AttributeManager
Note: Rename: / _list{0} = LSD / _list{1} = SEC / _list{2} = TWP / Remove: / _list{3}
AttributeManager
    ATTR_TABLE:
      RENAME_SET_VALUE _list{0} > LSD
      RENAME_SET_VALUE _list{1} > SEC
      RENAME_SET_VALUE _list{2} > TWP
      REMOVE _list{3}
    -> FeatureMerger [SUPPLIER]
