FME workspace Movies.fmw

Parameters:
- SourceDataset_XLSXR = $(FME_MF_DIR)Data\Greatest films of all time.xlsx   # Source Microsoft Excel File(s)
- SourceDataset_XLSXR_5 = C:\Users\lsanderson\Downloads\Interactive_Map_Data.xlsx   # Source Microsoft Excel File(s)
- SourceDataset_XLSXR_4 = C:\Users\lsanderson\Documents\100GreatestActorsOfAllTime-IMDB.xlsx   # Source Microsoft Excel File(s)
- SourceDataset_CSV2 = $(FME_MF_DIR)Data\Neighborhoods.csv   # Source CSV (Comma Separated Value) File(s)

Readers:
- XLSXR_1: XLSXR from $(SourceDataset_XLSXR)
- XLSXR_2: XLSXR from $(SourceDataset_XLSXR_5)
- XLSXR_3: XLSXR from $(SourceDataset_XLSXR_4)
- CSV2_1: CSV2 from $(SourceDataset_CSV2)

Note: CSV: Neighborhoods [CSV2]
CSV (reader CSV2_1)
    attributes: BoroName string, CountyFIPS string, the_geom string, BoroCode string, NTACode string, NTAName string, Shape_Leng string, Shape_Area string
    -> SubstringExtractor_2
SubstringExtractor_2
    SRC_STRING = @Value(the_geom)
    END = -4
    START = 16
    RESULT_ATTR = _substring
    -> AttributeSplitter
AttributeSplitter
    DROP_EMPTY_PARTS = No
    DELIMITER = ,
    ATTR_NAME = _substring
    LIST_NAME = _list
    TRIM_OPTION = None
    -> ListExploder
ListExploder
    LIST_ATTR = _list{}
    INDEX_ATTR = _element_index
    ATTR_CONFLICT_RES = Use List Attribute Values
    ATTR_ACCUM_MODE = Merge List Attributes
    ELEMENTS -> SubstringExtractor_2_Output
Sheet1 (reader XLSXR_3) [off]
    attributes: # number(4,0), Name char(23), Known For char(76), Birth Date date, Date date
    -> SubstringExtractor
SubstringExtractor [off]
    SRC_STRING = @Value(Known For)
    END = 50
    START = 7
    RESULT_ATTR = Movie
    -> FeatureMerger [SUPPLIER]
SubstringExtractor_Output: Inspector [off]

Bookmark: New Bookmark
SubstringExtractor_2_Output: Inspector
FeatureMerger
    ATTR_CONFLICT_RES = Use Requestor
    SUPPLIERS_FIRST = No
    IGNORE_NULLS = No
    JOIN_KEYS = @Value(Film) @Value(Movie) AUTO
    ATTR_ACCUM_MODE = Merge Supplier
    MERGE_TYPE = Attributes Only
    PROCESS_DUPS = No
    REJECT_NULL_MISSING_KEYS = No
    MERGED -> FeatureMerger_Merged
    UNMERGED_REQUESTOR -> FeatureMerger_UnmergedRequestor
    USED_SUPPLIER -> FeatureMerger_UsedSupplier
    UNUSED_SUPPLIER -> FeatureMerger_UnusedSupplier
    <REJECTED> -> FeatureMerger__Rejected_
FeatureMerger_Merged: Inspector
FeatureMerger_UnmergedRequestor: Inspector
FeatureMerger_UsedSupplier: Inspector
FeatureMerger_UnusedSupplier: Inspector
FeatureMerger__Rejected_: Inspector

Bookmark: New Bookmark
ARTHOUSE AND DRAMA (reader XLSXR_1) [off]
    attributes: Entry number(3,0), Film char(35), Director char(21), Leading actors char(105), Year of cinema release number(5,0), No of Oscars won char(13), IMDB link char(37), Guardian film page char(74), Country char(13)
    -> AttributeManager [off]
ROMANCE (reader XLSXR_1) [off]
    attributes: Entry number(3,0), Film char(38), Director char(36), Leading actors char(99), Year of cinema release number(5,0), No of Oscars won number(2,0), IMDB link char(43), Guardian film page char(82), Country char(10)
    -> AttributeManager [off]
HORROR (reader XLSXR_1) [off]
    attributes: Entry number(3,0), Film char(27), Director char(37), Leading actors char(105), Year of cinema release char(11), No of Oscars won number(2,0), IMDB link char(37), Guardian film page char(67), Country char(8)
    -> AttributeManager [off]
COMEDY (reader XLSXR_1) [off]
    attributes: Entry number(3,0), Cat char(7), Film char(29), Director char(44), Leading actors char(111), Year of cinema release number(5,0), Oscars won number(2,0), IMDB link char(37), Guardian film page char(72), Country char(4)
    -> AttributeManager [off]
CRIME (reader XLSXR_1) [off]
    attributes: Entry number(3,0), Film char(35), Director char(38), Leading actors char(146), Year of cinema release number(5,0), Oscars won number(2,0), IMDB link char(37), Guardian film page char(70), Country char(10), J string
    -> AttributeManager [off]
SCI-FI AND FANTASY (reader XLSXR_1) [off]
    attributes: Entry number(3,0), Film char(30), Director char(37), Leading actors char(179), Year of cinema release char(10), No of Oscars won char(14), IMDB link char(37), Guardian film page char(78), Country char(12)
    -> AttributeManager [off]
ACTION (reader XLSXR_1) [off]
    attributes: Entry number(3,0), Film char(30), Director char(33), Leading actors char(113), Year of cinema release number(5,0), No of Oscars won number(2,0), IMDB link char(37), Guardian film page char(78), Country char(7)
    -> AttributeManager [off]
AttributeManager [off]
    ATTR_TABLE:
      REMOVE Entry
      REMOVE Guardian film page
      RENAME_SET_VALUE fme_feature_type > Genre
      REMOVE Oscars won
      REMOVE J
      REMOVE Cat

Bookmark: New Bookmark
Full Map List (reader XLSXR_2) [off]
    attributes: Film char(38), Year char(12), URL Encoded name char(48), Image File Name char(24), Agency Credit char(37), Artist Credit char(12), Director/Filmmaker Name char(37), Director/Filmmaker IMDB Link char(126), Location Display Text char(90), LATITUDE y_coordinate, LONGITUDE x_coordinate, Borough char(14), Neighborhood char(20), Scene Type char(21), Media char(5), IMDB LINK char(37), Client or book location indicator char(78), Notes char(39), Book Image char(2), Book Page char(8), Display? char(2), IMAGE OF LOCATION char(2)
    -> AttributeManager_2
AttributeManager_2 [off]
    ATTR_TABLE:
      REMOVE URL Encoded name
      REMOVE Image File Name
      REMOVE Agency Credit
      REMOVE Artist Credit
      REMOVE Scene Type
      REMOVE Media
      REMOVE Client or book location indicator
      REMOVE Notes
      REMOVE Book Image
      REMOVE Book Page
      REMOVE Display?
      REMOVE IMAGE OF LOCATION
    -> FeatureMerger [REQUESTOR]
    -> AttributeManager_2_Output
AttributeManager_2_Output: Inspector [off]
