FME workspace 2-MovieBudget.fmw

Parameters:
- DestDataset_XLSXW = $(FME_MF_DIR)Output\Budgets.xlsx   # Destination Microsoft Excel File
- SourceDataset_CSV2_3 = $(FME_MF_DIR)Data\MovieBudget.csv   # Source CSV (Comma Separated Value) File(s)

Readers:
- CSV2_1: CSV2 from $(SourceDataset_CSV2_3)

Writers:
- XLSXW_1: XLSXW to $(DestDataset_XLSXW)

Note: CSV: MovieBudget [CSV2]
Note: Data Attribution: / MovieBudget.csv - Budget and gross data from The Numbers http://www.the-numbers.com/ / NewYorkFilmingLocations.xlsx - Filming locations in NYC. from NYC Open Data https://opendata.cityofnewyork.us/
CSV (reader CSV2_1)
    attributes: Rank string, Release Date string, Movie string, Production Budget string, Domestic Gross string, Worldwide Gross string
    -> DateTimeConverter
Note: MovieTotalGross: Budgets [XLSXW]
MovieTotalGross (writer XLSXW_1)
    attributes: Movie string(20), Year auto(20), Release Date string(20), Domestic Gross string(20), Worldwide Gross string(20), Production Budget string(20), Borough auto(20), Neighborhood auto(20), Director/Filmmaker Name auto(20), Location Display Text auto(20), LONGITUDE auto(20), LATITUDE auto(20), International Gross auto(20)

Bookmark: Clean up date and extract Year
Note: Clean up date
DateTimeConverter
    DATETIME_ATTR = Release Date
    REPAIR_INPUT = NO
    IN_FORMAT = %N/%e/%Y
    OUT_FORMAT = %Y/%m/%d
    -> SubstringExtractor
Note: Extract year to ensure we match with the correct movie
SubstringExtractor
    RESULT_ATTR = Year
    START = 0
    SRC_STRING = @Value(Release Date)
    END = 3
    -> DatabaseJoiner

Bookmark: Join with Interactive_Map_Data.xlsx
Note: Join with NewYorkFilmingLocations.xlsx / Join on Movie/Film and Year/Year / Add attribute fields: Borough, Year, Filmmaker Name, Latitude, Longitude, Location Display Text, and Neighborhood
DatabaseJoiner
    XLSXR_READ_BLANK_AS = Missing
    XLSXR_CASE_SENSITIVE_FEATURE_TYPES = YES
    XLSXR_USE_SCHEMA_OTHER_FILES = No
    XLSXR_CONFIGURATION_DATASET = C:/Users/lsanderson/Documents/SafeProjects/Webinars/BusinessIntelligence/Webinar/Data/NewYorkFilmingLocations.xlsx
    XLSXR_QUERY_FEATURE_TYPES_FOR_MERGE_FILTERS = Yes
    XLSXR_ALLOW_DOLLAR_SIGNS = YES
    ATTR_CONFLICT_RES = Use Original
    JOIN_KEYS = Movie Film Year Year
    ADDED_FIELDS = Borough "Director/Filmmaker Name" LATITUDE "Location Display Text" LONGITUDE Neighborhood
    DATASET = $(FME_MF_DIR_ENCODED)Data\NewYorkFilmingLocations.xlsx
    XLSXR_FORCE_DATETIME = NO
    ATTR_ACCUM_MODE = Merge Joined
    MATCH_MULTIPLE_DISPLAY = Create a feature for each match
    FORMAT = XLSXR
    MATCH_RULE_DISPLAY = Match All (1:M)
    XLSXR_SCAN_SCHEMA_IF_DYNAMIC = No
    XLSXR_EXPOSED_ATTRS = xlsx_row_id,number(11,0)
    TABLE = Full Map List
    XLSXR_EXPAND_MERGED_CELLS = Yes
    XLSXR_SCHEMA = Full Map List,0,Film,char,38,,,1,Year,char,12,,,2,"URL Encoded name",char,48,,,3,"Image File Name",char,24,,,4,"Agency Credit",char,37,,,5,"Artist Credit",char,12,,,6,"Director/Filmmaker Name",char,37,,,7,"Director/Filmmaker IMDB Link",char,126,,,8,"Location Display Text",char,90,,,9,LATITUDE,y_coordinate,,,,10,LONGITUDE,x_coordinate,,,,11,Borough,char,14,,,12,Neighborhood,char,20,,,13,"Scene Type",char,21,,,14,Media,char,5,,,15,"IMDB LINK",char,37,,,16,"Client or book location indicator",char,78,,,17,Notes,char,39,,,18,"Book Image",char,2,,,19,"Book Page",char,8,,,20,Display?,char,2,,,21,"IMAGE OF LOCATION",char,2,,,3,,,,NO,NO,3,C:/Users/lsanderson/Documents/SafeProjects/Webinars/BusinessIntelligence/Webinar/Data/NewYorkFilmingLocations.xlsx,"0,1,21,235","""Notable Directors"",""Items without location""",NO
    XLSXR_EXCEL_COL_NAMES = YES
    XLSXR_TABLELIST = "Full Map List"
    JOINED -> DuplicateFilter
Note: Remove duplicate movie titles based on location text
DuplicateFilter
    KEYATTR = Movie
    INPUT_ORDERED_CHOICE = No
    UNIQUE -> Tester

Bookmark: Data Cleanup to change from String to Number
Note: Test out $0 values
Tester
    BOOL_OP = OR
    TEST_CLAUSE:
      TEST @Value(Domestic Gross) NOT_BEGINS_WITH $0
      TEST @Value(Worldwide Gross) NOT_BEGINS_WITH $0
    TEST_DESCRIPTION = ""
    TEST_MODE = Automatic
    PASSED -> StringReplacer
Note: Replace $ with nothing
StringReplacer
    CASE = NO
    REGEXP = NO
    FIND_TEXT = $
    NO_MATCH = _FME_NO_OP_
    SRC_ATTRS = "Worldwide Gross","Production Budget","Domestic Gross"
    -> StringReplacer_2
Note: Replace , with nothing
StringReplacer_2
    CASE = NO
    REGEXP = NO
    FIND_TEXT = ,
    NO_MATCH = _FME_NO_OP_
    SRC_ATTRS = "Worldwide Gross","Production Budget","Domestic Gross"
    -> AttributeManager
Note: Reorder attributes and removed _matched_record that was created with the DatabaseJoiner
AttributeManager
    ATTR_TABLE:
      REMOVE _matched_records
      REMOVE Rank
    -> ExpressionEvaluator

Bookmark: Calculate International Gross and Sort
Note: Subtract Domesitc Gross from Worldwide Gross and create a new attribute called International Gross. This could also be done in the Attribute Manager
ExpressionEvaluator
    EXPRESSION = @Value(Worldwide Gross)-@Value(Domestic Gross)
    ACTION = Create New Attribute
    VAL_ATTR = International Gross
    -> Sorter
Note: Sort Worldwide Gross so it is decending in value.
Sorter
    SORT_PARM = "Worldwide Gross" NUMERIC DESCENDING
    SORTED -> MovieTotalGross (writer XLSXW_1)
