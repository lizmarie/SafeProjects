FME workspace 3-MoviePosters.fmw

Parameters:
- SourceDataset_XLSXR_5 = $(FME_MF_DIR)Data\NewYorkFilmingLocations.xlsx   # Source Microsoft Excel File(s)
- DestDataset_XLSXW = $(FME_MF_DIR)Output\MoviePosters.xlsx   # Destination Microsoft Excel File

Readers:
- XLSXR_1: XLSXR from $(SourceDataset_XLSXR_5)

Writers:
- XLSXW_1: XLSXW to $(DestDataset_XLSXW)

Note: Full Map List: NewYorkFilmingLocations [XLSXR]
Note: Data Attribution: / NewYorkFilmingLocations.xlsx - Filming locations in NYC. from NYC Open Data https://opendata.cityofnewyork.us/ / Movie posters urls from The Internet Movie Database http://www.imdb.com/
Full Map List (reader XLSXR_1)
    attributes: Film char(38), Year char(12), URL Encoded name char(48), Image File Name char(24), Agency Credit char(37), Artist Credit char(12), Director/Filmmaker Name char(37), Director/Filmmaker IMDB Link char(126), Location Display Text char(90), LATITUDE y_coordinate, LONGITUDE x_coordinate, Borough char(14), Neighborhood char(20), Scene Type char(21), Media char(5), IMDB LINK char(37), Client or book location indicator char(78), Notes char(39), Book Image char(2), Book Page char(8), Display? char(2), IMAGE OF LOCATION char(2)
    -> HTTPCaller
Note: Template File: MoviePosters-Template.xlsx
Note: MoviePosters: MoviePosters [XLSXW]
MoviePosters (writer XLSXW_1)
    attributes: Film string(38), Year string(12), Director/Filmmaker Name string(37), Location Display Text string(90), LATITUDE number(20), LONGITUDE number(20), Borough string(14), Neighborhood string(20), MoviePoster auto(20)

Bookmark: Extract HTML from IMDB and then extract the Movie Poster URL
Note: Use IMBD link
HTTPCaller
    ERROR_ATTR = _error
    TARGET_ATTR = _response_body
    CONNECTION_TIMEOUT_LENGTH = 60
    FOLLOW_REDIRECTS = Yes
    RESPONSE_HEADER_LIST_ATTR = _headers
    STATUS_CODE_ATTR = _http_status_code
    SAVE_FILE = Attribute
    USE_COOKIES = No
    TRANSFER_TIMEOUT_LENGTH = 90
    VERIFY_SSL_CERTIFICATES = Yes
    TARGET_URL = @Value(IMDB LINK)
    TARGET_ATTR_ENCODING = auto-detect
    HTTP_METHOD = GET
    -> HTMLExtractor
Note: Extract the html containing the image using the CSS selector .poster
HTMLExtractor
    SEARCH_TABLE = poster .poster Value
    HTML_SPECIFICATION = Content
    HTML_FIELD = @Value(_response_body)
    RESULT_TYPE_NAME = FIRST_MATCH
    Results -> StringSearcher_2
Note: Extract only the URL from the html using regex / http.+?(?=).jpg
StringSearcher_2
    CASE = no
    MATCHED_RESULT_ATTR = MoviePoster
    REGEXP = http.+?(?=).jpg
    STRING_TO_SEARCH = @Value(poster)
    MATCHED -> AttributeCreator_2

Bookmark: Add Movie Poster Image into Excel
Note: Create an attribute to contain the movie poster in the excel document
AttributeCreator_2
    ATTR_TABLE:
      SET_TO xlsx_col_id = 8
      SET_TO xlsx_raster_height = 200
      SET_TO xlsx_raster_width = 200
      SET_TO xlsx_row_id = @Count(row_id,2)
    -> ImageFetcher_3
Note: Create an image using the Movie Poster URL
Note: Knowedge Base Article: Writing Images to an Excel Spreadsheet
ImageFetcher_3
    FOLLOW_REDIRECTS = Yes
    CONNECTION_TIMEOUT_LENGTH = 60
    USE_COOKIES = No
    RASTER_TYPE = <Auto-Detect from HTTP Headers>
    TRANSFER_TIMEOUT_LENGTH = 90
    ERROR_ATTR = _http_error
    VERIFY_SSL_CERTIFICATES = Yes
    STATUS_CODE_ATTR = _http_status_code
    RESPONSE_HEADER_LIST_ATTR = _http_headers
    URL = @Value(MoviePoster)
    RASTER -> StringReplacer

Bookmark: Clean up attributes
Note: Remove <br> from Location Text
StringReplacer
    CASE = NO
    FIND_TEXT = <br>
    NO_MATCH = _FME_NO_OP_
    SRC_ATTRS = "Location Display Text"
    REGEXP = NO
    REPLACE_TEXT = " "
    -> AttributeManager_4
Note: Remove extra attributes from excel file, HTTPCaller and HTMLExtractor
AttributeManager_4
    ATTR_TABLE:
      REMOVE IMDB LINK
      REMOVE _headers{}.name
      REMOVE _headers{}.value
      REMOVE _response_body
      REMOVE _http_status_code
      REMOVE poster
      REMOVE URL Encoded name
      REMOVE Image File Name
      REMOVE Agency Credit
      REMOVE Artist Credit
      REMOVE Director/Filmmaker IMDB Link
      REMOVE Scene Type
      REMOVE Media
      REMOVE Client or book location indicator
      REMOVE Notes
      REMOVE Book Image
      REMOVE Book Page
      REMOVE Display?
      REMOVE IMAGE OF LOCATION
      REMOVE fme_basename
    -> MoviePosters (writer XLSXW_1)
